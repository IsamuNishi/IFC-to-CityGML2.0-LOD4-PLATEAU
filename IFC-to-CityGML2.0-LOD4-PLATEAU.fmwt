FME workspace IFC-to-CityGML2.0-LOD4-PLATEAU.fmwt
Title: IFC to CITYGML
History: 2022-10-07,Takashi Iijima, PSS,v1,2022-11-10,Takashi Iijima, PSS,v2: BuildingInstallation,intBuildingInstallation, BuildingFurniture

Parameters:
- SourceDataset_IFC = C:\Users\takas\PSS Dropbox\Products\06_FME\support\コンサルティングサービス\202207-001_日建設計\20230216\20230216_新サンプル\DGT_NKS_ARC_PLN_ZZ_V21_ZZ_230216.ifc   # Source Industry Foundation Class (IFC) File(s)
- IUR_SCHEMA_XSD = C:\Users\takas\PSS Dropbox\Products\06_FME\support\コンサルティングサービス\202207-001_日建設計\20230216\schema\urbanObject.xsd   # i-UR Schema File (urbanObject.xsd)
- DestDataset_CITYGML_3 = $(FME_MF_DIR)output\nikken.gml   # Destination CityGML Dataset (*.gml)
- DEST_LOD = 4.0   # Destination LOD
- DEST_COORDSYS =   # Destination Coordinate System
- REPROJECTION_MODE = None   # Reprojection Mode
- GRP_REPROJECTION =   # Reprojection Parameters (Set for Manual mode)
- LENGTH_UNITS =   # Length Units of Data
- CRS_NAME =   # CRS Name (EPSG:xxxx)
- EASTINGS =   # Eastings
- NORTHINGS =   # Northings
- ORTHOBONAL_HEIGHT =   # Orthogonal Height
- XAXIS_ABSCISSA =   # X Axis Abscissa
- XAXIS_ORDINATE =   # X Axis Ordinate
- SCALE =   # Scale

Readers:
- IFC_1: IFC from $(SourceDataset_IFC)

Writers:
- CITYGML_2: CITYGML to $(DestDataset_CITYGML_3)

Creator
    GEOMTYPE = Geometry Object
    NUM = 1
    CREATED -> ParameterFetcher
ParameterFetcher
    ATTR_LIST = _lengthunit $(LENGTH_UNITS) ProjectedCRS.Name $(CRS_NAME) MapConversion.Eastings $(EASTINGS) MapConversion.Northings $(NORTHINGS) MapConversion.OrthogonalHeight $(ORTHOBONAL_HEIGHT) MapConversion.XAxisAbscissa $(XAXIS_ABSCISSA) MapConversion.XAxisOrdinate $(XAXIS_ORDINATE) MapConversion.Scale $(SCALE)
    -> Tester_8
Note: _building_id: 建物ごとのユニークなID / -> 建築物の gml_id / -> 壁、屋根などの gml_parent_id
AttributeManager_17
    ATTR_TABLE:
      SET_TO _building_id = bldg_@UUID()
      REMOVE ProjectedCRS.Name
      REMOVE MapConversion.Eastings
      REMOVE MapConversion.Northings
      REMOVE MapConversion.OrthogonalHeight
      REMOVE MapConversion.XAxisAbscissa
      REMOVE MapConversion.XAxisOrdinate
      REMOVE MapConversion.Scale
    -> FeatureMerger_4 [SUPPLIER]
Note: Read IfcSpace Geometries: Yes / Subtract Opening Geometries: No / Evaluate CSG Solids: Yes / Simplify Extrusion Base Faces: Yes
IfcBuilding (reader IFC_1)
    attributes: GlobalId char(22), Name string, Description string, ObjectType string, LongName string, CompositionType string, ElevationOfRefHeight real, ElevationOfTerrain real, BuildingAddress.Purpose enumeration, BuildingAddress.Description string, BuildingAddress.UserDefinedPurpose string, BuildingAddress.InternalLocation string, BuildingAddress.AddressLines string, BuildingAddress.PostalBox string, BuildingAddress.Town string, BuildingAddress.Region string, BuildingAddress.PostalCode string, BuildingAddress.Country string, Axis geometry, Body geometry, Box geometry, FootPrint geometry, ApplicableOccurrence string, ElementType string, Elevation real, ElevationWithFlooring real, InteriorOrExteriorSpace enumeration, LandTitleNumber string, NumberOfRiser int, NumberOfTreads int,
      OverallHeight real, OverallWidth real, Phase string, PredefinedType enumeration, RefElevation real, RefLatitude real, RefLongitude real, RiserHeight real, ShapeType enumeration, SiteAddress.AddressLines string, SiteAddress.Country string, SiteAddress.Description string, SiteAddress.InternalLocation string, SiteAddress.PostalBox string, SiteAddress.PostalCode string, SiteAddress.Purpose enumeration, SiteAddress.Region string, SiteAddress.Town string, SiteAddress.UserDefinedPurpose string, Tag string, TreadLength real, ifc_type_name string, ifc_type_object_id string
    -> AttributeCopier
Note: _ifc_feature_type = fme_feature_type
AttributeCopier
    ATTR_TABLE = COPY fme_feature_type > _ifc_feature_type
    MISSING_INPUT_ATTRS = REMOVE
    -> FeatureMerger_4 [REQUESTOR]
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> TestFilter_3
TestFilter_3
    DEFAULT_VALUE = <UNFILTERED>
    PASSED_TEST_GROUP_OUTPUT = FIRST
    TEST_LIST = "BOOL_OP,AND,COMPOSITE_TEST,""""""1"""""",TEST_CLAUSE,TEST $(REPROJECTION_MODE) = Manual",Manual,"BOOL_OP,OR,COMPOSITE_TEST,""""""1"""""",TEST_CLAUSE,TEST $(REPROJECTION_MODE) = Auto",Automatic,"BOOL_OP,OR,COMPOSITE_TEST,""""""1"""""",TEST_CLAUSE,TEST $(REPROJECTION_MODE) = None",None
    Manual -> Tester_7
    Automatic -> PLATEAU.IfcReprojectionParamsExtractor [IfcFeatures]
    None -> CoordinateSystemRemover
Note: Tester : Input
Junction_68
    -> Junction_69
Note: FeatureMerger_6 : Merged
Junction_69
    -> Tester
Tester_7
    BOOL_OP = OR
    TEST_CLAUSE = TEST @Value(_reprojection_params) TYPE JSON
    TEST_MODE = TEST
    PASSED -> FeatureTypeFilter_5
    FAILED -> Terminator_2
FeatureTypeFilter_5
    ATTRIBUTES = IfcProject,<Unfiltered>,<Blank>
    IfcProject -> Junction_37
    <UNFILTERED> -> Tester
Terminator_2
    MESSAGE = Translation Terminated
PLATEAU.IfcReprojectionParamsExtractor
    IfcProject -> Junction_37
    Others -> Tester
    <Rejected> -> Terminator
Junction_37
    -> AttributeManager_16
AttributeManager_16
    ATTR_TABLE:
      REMOVE CompositionType
      REMOVE ElevationOfRefHeight
      REMOVE ElevationOfTerrain
      REMOVE BuildingAddress.Purpose
      REMOVE BuildingAddress.Description
      REMOVE BuildingAddress.UserDefinedPurpose
      REMOVE BuildingAddress.InternalLocation
      REMOVE BuildingAddress.AddressLines
      REMOVE BuildingAddress.PostalBox
      REMOVE BuildingAddress.Town
      REMOVE BuildingAddress.Region
      REMOVE BuildingAddress.PostalCode
      REMOVE BuildingAddress.Country
      REMOVE Body
      REMOVE Elevation
      REMOVE ElevationWithFlooring
      REMOVE InteriorOrExteriorSpace
      REMOVE LandTitleNumber
      REMOVE OverallHeight
      REMOVE OverallWidth
      REMOVE Phase
      REMOVE PredefinedType
      REMOVE RefElevation
      REMOVE RefLatitude
      REMOVE RefLongitude
      REMOVE ShapeType
      REMOVE SiteAddress.AddressLines
      REMOVE SiteAddress.Country
      REMOVE SiteAddress.Description
      REMOVE SiteAddress.InternalLocation
      REMOVE SiteAddress.PostalBox
      REMOVE SiteAddress.PostalCode
      REMOVE SiteAddress.Purpose
      REMOVE SiteAddress.Region
      REMOVE SiteAddress.Town
      REMOVE SiteAddress.UserDefinedPurpose
      REMOVE Tag
      REMOVE ifc_parent_id
      REMOVE ifc_parent_unique_id
      REMOVE fme_feature_type
      REMOVE _reprojection_params
      REMOVE IfcProject.GlobalId
      REMOVE IfcProject.OwnerHistory
      REMOVE IfcProject.Name
      REMOVE IfcProject.Description
      REMOVE IfcProject.ObjectType
      REMOVE IfcProject.LongName
      REMOVE ProjectedCRS.Name
      REMOVE ProjectedCRS.Description
      REMOVE ProjectedCRS.GeodeticDatum
      REMOVE ProjectedCRS.VerticalDatum
      REMOVE ProjectedCRS.MapProjection
      REMOVE ProjectedCRS.MapZone
      REMOVE MapConversion.Eastings
      REMOVE MapConversion.Northings
      REMOVE MapConversion.OrthogonalHeight
      REMOVE MapConversion.XAxisAbscissa
      REMOVE MapConversion.XAxisOrdinate
      REMOVE MapConversion.Scale
      REMOVE Axis
      REMOVE Box
      REMOVE FootPrint
      REMOVE NumberOfRiser
      REMOVE NumberOfTreads
      REMOVE RiserHeight
      REMOVE TreadLength
      REMOVE ApplicableOccurrence
      REMOVE ElementType
      REMOVE ifc_type_name
      REMOVE ifc_type_object_id
    -> XMLTemplater [ROOT]
Tester
    BOOL_OP = OR
    TEST_CLAUSE = TEST ifc_parent_unique_id ATTRIBUTE_HAS_A_VALUE ""
    TEST_MODE = TEST
    PASSED -> AttributeManager
Note: gml_description, gml_name 設定 / 後続の処理で使う属性以外を削除
AttributeManager
    ATTR_TABLE:
      RENAME_SET_VALUE Description > gml_description
      SET_TO gml_name = FME_CONDITIONAL:DEFAULT_VALUE'@Value(Name)'BOOL_OP;OR;COMPOSITE_TEST;1;TEST LongName ATTRIBUTE_HAS_A_VALUE _FME_BLANK_STRING_'@Value(LongName)'FME_NUM_CONDITIONS2___
      REMOVE ElevationOfRefHeight
      REMOVE ElevationOfTerrain
      REMOVE BuildingAddress.Purpose
      REMOVE BuildingAddress.Description
      REMOVE BuildingAddress.UserDefinedPurpose
      REMOVE BuildingAddress.InternalLocation
      REMOVE BuildingAddress.AddressLines
      REMOVE BuildingAddress.PostalBox
      REMOVE BuildingAddress.Town
      REMOVE BuildingAddress.Region
      REMOVE BuildingAddress.PostalCode
      REMOVE BuildingAddress.Country
      REMOVE Axis
      REMOVE Body
      REMOVE Box
      REMOVE FootPrint
      REMOVE Phase
      REMOVE PredefinedType
      REMOVE RefElevation
      REMOVE RefLatitude
      REMOVE RefLongitude
      REMOVE RiserHeight
      REMOVE ShapeType
      REMOVE SiteAddress.AddressLines
      REMOVE SiteAddress.Country
      REMOVE SiteAddress.Description
      REMOVE SiteAddress.InternalLocation
      REMOVE SiteAddress.PostalBox
      REMOVE SiteAddress.PostalCode
      REMOVE SiteAddress.Purpose
      REMOVE SiteAddress.Region
      REMOVE SiteAddress.Town
      REMOVE SiteAddress.UserDefinedPurpose
      REMOVE TreadLength
      REMOVE ifc_parent_id
    -> GeometryCoercer
    -> XMLTemplater [SUB]
    -> Tester_11
CoordinateRounder
    XPREC = @Value(_coordinate_precision)
    YPREC = @Value(_coordinate_precision)
    ZPREC = @Value(_coordinate_precision)
    ROUNDED -> FeatureTypeFilter
    ROUNDED -> AttributeManager_18
AttributeManager_18
    ATTR_TABLE:
      SET_TO gml_description = @Value(Description)
      SET_TO gml_name = FME_CONDITIONAL:DEFAULT_VALUE'@Value(Name)'BOOL_OP;OR;COMPOSITE_TEST;1;TEST LongName ATTRIBUTE_HAS_A_VALUE _FME_BLANK_STRING_'@Value(LongName)'FME_NUM_CONDITIONS2___
      REMOVE Description
      REMOVE CompositionType
      REMOVE Elevation
      REMOVE ElevationWithFlooring
      REMOVE InteriorOrExteriorSpace
      REMOVE LandTitleNumber
      REMOVE ApplicableOccurrence
      REMOVE ElementType
      REMOVE ifc_type_name
      REMOVE ifc_type_object_id
      SET_TO
      REMOVE NumberOfRiser
      REMOVE NumberOfTreads
    -> PLATEAU.IfcAttributeExtractor
Note: 属性抽出 : Under developing
PLATEAU.IfcAttributeExtractor
    Window -> Junction_54
    Door -> Junction_57
Junction_54
    -> Junction_55
Note: PLATEAU.IfcAttributeExtractor : Window
Junction_55
    -> FeatureMerger_AttrWindow [SUPPLIER]
Note: PLATEAU.IfcAttributeExtractor : Door
Junction_57
    -> FeatureMerger_AttrDoor [SUPPLIER]
Note: 壁 / IfcWali / IfcWallStandardCase / IfcCurtainWall / IfcPlate / IfcColumn
FeatureTypeFilter
    ATTRIBUTES = IfcOpeningElement,IfcDoor,IfcWindow,IfcWall,IfcWallStandardCase,IfcCurtainWall,IfcColumn,IfcPlate,IfcRoof,IfcSlab,IfcSpace,IfcBeam,IfcStair,IfcStairFlight,IfcRamp,IfcRampFlight,IfcRailing,IfcBuildingElementProxy,IfcTransportElement,IfcFurnishingElement,<Unfiltered>,<Blank>
    ATTRIBUTE_INFO = IfcBuilding,GlobalId,Name,Description,ObjectType,LongName,CompositionType,ElevationOfRefHeight,ElevationOfTerrain,BuildingAddress.Purpose,BuildingAddress.Description,BuildingAddress.UserDefinedPurpose,BuildingAddress.InternalLocation,BuildingAddress.AddressLines,BuildingAddress.PostalBox,BuildingAddress.Town,BuildingAddress.Region,BuildingAddress.PostalCode,BuildingAddress.Country,Axis,Body,Box,FootPrint,Elevation,ElevationWithFlooring,InteriorOrExteriorSpace,LandTitleNumber,NumberOfRiser,NumberOfTreads,OverallHeight,OverallWidth,Phase,PredefinedType,RefElevation,RefLatitude,RefLongitude,RiserHeight,ShapeType,SiteAddress.AddressLines,SiteAddress.Country,SiteAddress.Description,SiteAddress.InternalLocation,SiteAddress.PostalBox,SiteAddress.PostalCode,SiteAddress.Purpose,SiteAddress.Region,SiteAddress.Town,SiteAddress.UserDefinedPurpose,Tag,TreadLength,ifc_parent_id,ifc_parent_unique_id,ifc_unique_id,fme_feature_type
    IfcOpeningElement -> Deaggregator_5
    IfcDoor -> Junction
    IfcWindow -> Junction
    IfcWall -> Junction_62
    IfcWallStandardCase -> Junction_62
    IfcCurtainWall -> Junction_62
    IfcColumn -> Junction_64
    IfcPlate -> Tester_IfcPlate
    IfcRoof -> Junction_65
    IfcSlab -> Tester_9
    IfcSpace -> Junction_45
    IfcBeam -> Tester_IfcBeam
    IfcStair -> Junction_66
    IfcStairFlight -> Junction_66
    IfcRamp -> Junction_66
    IfcRampFlight -> Junction_66
    IfcRailing -> Tester_IfcRailing
    IfcBuildingElementProxy -> Junction_66
    IfcTransportElement -> Junction_66
    IfcFurnishingElement -> Tester_IfcFurnishingElement
Junction
    -> AttributeManager_20
AttributeManager_20
    ATTR_TABLE:
      REMOVE gml_description
      REMOVE gml_name
      REMOVE GlobalId
      REMOVE Name
      REMOVE ObjectType
      REMOVE LongName
      REMOVE CompositionType
      REMOVE Elevation
      REMOVE ElevationWithFlooring
      REMOVE InteriorOrExteriorSpace
      REMOVE LandTitleNumber
      REMOVE NumberOfRiser
      REMOVE NumberOfTreads
      REMOVE OverallHeight
      REMOVE OverallWidth
      REMOVE Tag
      REMOVE ApplicableOccurrence
      REMOVE ElementType
      REMOVE ifc_type_name
      REMOVE ifc_type_object_id
      REMOVE _lengthunit
      REMOVE _reprojection_params
      REMOVE _lengthmultiplier
      REMOVE _coordinate_precision
      REMOVE fme_feature_type
      REMOVE fme_basename
      REMOVE Description
      REMOVE _storey_name
      REMOVE _parent_feature_type
      REMOVE _storey_index
    -> FeatureMerger_7 [SUPPLIER]
Note: OpeningElement に関連する Door, Window の ID を与える。 / prefix : _opening_ / Roor, Window がない場合の _opening_ 属性は OpeningElement から引き継ぐ 。
FeatureMerger_7
    ATTR_ACCUM_MODE = Prefix Supplier
    GROUP_BY = _building_id
    IGNORE_NULLS = No
    JOIN_KEYS = @Value(ifc_unique_id) @Value(ifc_parent_unique_id) AUTO
    MERGE_TYPE = Attributes Only
    PROCESS_DUPS = NO
    REJECT_NULL_MISSING_KEYS = No
    SUPPLIERS_FIRST = No
    SUPPLIER_PREFIX = _opening_
    MERGED -> AttributeManager_21
    UNMERGED_REQUESTOR -> AttributeManager_22
AttributeManager_21
    ATTR_TABLE:
      REMOVE gml_description
      REMOVE gml_name
      REMOVE GlobalId
      REMOVE Name
      REMOVE ObjectType
      REMOVE LongName
      REMOVE CompositionType
      REMOVE Elevation
      REMOVE ElevationWithFlooring
      REMOVE InteriorOrExteriorSpace
      REMOVE LandTitleNumber
      REMOVE NumberOfRiser
      REMOVE NumberOfTreads
      REMOVE OverallHeight
      REMOVE OverallWidth
      REMOVE Tag
      REMOVE ifc_parent_unique_id
      REMOVE ifc_unique_id
      REMOVE ApplicableOccurrence
      REMOVE ElementType
      REMOVE ifc_type_name
      REMOVE ifc_type_object_id
      REMOVE _lengthunit
      REMOVE _reprojection_params
      REMOVE _ifc_feature_type
      REMOVE _lengthmultiplier
      REMOVE _coordinate_precision
      REMOVE fme_feature_type
      REMOVE fme_basename
      REMOVE Description
      REMOVE _storey_name
      REMOVE _parent_feature_type
      REMOVE _opening__building_id
      REMOVE _opening_ifc_parent_unique_id
      RENAME_SET_VALUE _opening__ifc_feature_type > _opening_ifc_feature_type
      REMOVE _opening__storey_id
    -> Junction_5
AttributeManager_22
    ATTR_TABLE:
      REMOVE gml_description
      REMOVE gml_name
      REMOVE GlobalId
      REMOVE Name
      REMOVE ObjectType
      REMOVE LongName
      REMOVE CompositionType
      REMOVE Elevation
      REMOVE ElevationWithFlooring
      REMOVE InteriorOrExteriorSpace
      REMOVE LandTitleNumber
      REMOVE NumberOfRiser
      REMOVE NumberOfTreads
      REMOVE OverallHeight
      REMOVE OverallWidth
      REMOVE Tag
      REMOVE ifc_parent_unique_id
      RENAME_SET_VALUE ifc_unique_id > _opening_ifc_unique_id
      REMOVE ApplicableOccurrence
      REMOVE ElementType
      REMOVE ifc_type_name
      REMOVE ifc_type_object_id
      REMOVE _lengthunit
      REMOVE _reprojection_params
      RENAME_SET_VALUE _ifc_feature_type > _opening_ifc_feature_type
      REMOVE _lengthmultiplier
      REMOVE _coordinate_precision
      REMOVE fme_feature_type
      REMOVE fme_basename
      REMOVE Description
      REMOVE _storey_name
      REMOVE _parent_feature_type
    -> Junction_5
    -> Junction_60
Note: 屋外壁面 および / 屋内空間境界面をクリップ
Junction_5
    -> Junction_11
    -> Junction_13
Junction_13
    -> Clipper [CLIPPER]
Junction_11
    -> Clipper_2 [CLIPPER]
Note: Slab をクリップ
Junction_60
    -> Junction_59
Junction_62
    -> Junction_53
Tester_IfcPlate
    BOOL_OP = OR
    TEST_CLAUSE = TEST $(DEST_LOD) = 4.3
    TEST_MODE = TEST
    PASSED -> Junction_53
Junction_53
    -> Junction_12
Junction_64
    -> Junction_49
Junction_49
    -> Junction_12
    -> Junction_38
Junction_12
    -> Deaggregator
w3: Inspector [off]
    TACKATTRS = _storey_id
w2: Inspector [off]
    TACKATTRS = _storey_id
w1: Inspector [off]
    TACKATTRS = _storey_id
Note: GeometryExtractor_3
Junction_38
    -> Junction_39
Note: IfcColumn
Junction_39
    -> GeometryRefiner
GeometryRefiner
    -> GeometryExtractor_3
GeometryExtractor_3
    ATTR = _geometry
    KIND_LONG = FME Binary
    REMOVE_GEOMETRY = No
    -> SurfaceFootprintReplacer_7
SurfaceFootprintReplacer_7
    OFFSET_Z = 0
    SHADOW_MODE = Overhead Shadow
    FOOTPRINT -> SpatialFilter_4 [Candidate]
    <REJECTED> -> Junction_46
Junction_46
Junction_65
    -> Junction_30
Tester_9
    BOOL_OP = OR
    TEST_CLAUSE = TEST @Value(_parent_feature_type) = IfcRoof
    TEST_MODE = TEST
    PASSED -> Junction_30
    FAILED -> Deaggregator_3
Junction_30
    -> Junction_51
Junction_51
    -> Junction_52
Note: FeatureTypeFilter : IfcRoof
Junction_52
    -> GeometryPartExtractor_8
GeometryPartExtractor_8
    GQUERY:
      for $geom in //geometry
      where $geom/@fme_geometry_type = 'IFMEFace'
      return number($geom/@fme_id)
    EXTRACTED -> SurfaceSplitter_3
SurfaceSplitter_3
    FRONT -> TestFilter_2
Junction_22
    -> Junction_23
Note: スラブソリッド
Junction_23
    -> GeometryPartExtractor_7
    -> Clipper_4 [CLIPPER]
Note: Ceiling, Floor の Closure 抽出へ
Junction_74
    -> Junction_75
Note: Slab
Junction_75
    -> GeometryPartExtractor_10
Junction_45
    -> Deaggregator_2
Junction_4
    -> Junction_16
Note: Aggregator_2 : Input
Junction_16
    -> Junction_20
Note: Junction_4 : Output
Junction_20
    -> Aggregator_2
    -> Tester_6
m2: Inspector [off]
    TACKATTRS = _storey_id
FeatureMerger_3
    ATTR_ACCUM_MODE = Merge Supplier
    ATTR_CONFLICT_RES = Use Requestor
    GROUP_BY = _building_id
    IGNORE_NULLS = No
    JOIN_KEYS = @Value(_storey_id) @Value(_storey_id) AUTO
    MERGE_TYPE = Attributes Only
    PROCESS_DUPS = NO
    REJECT_NULL_MISSING_KEYS = No
    SUPPLIERS_FIRST = No
    MERGED -> Extruder
Note: 不要な属性を削除
AttributeKeeper
    CREATE_BULK_MODE_FEATURES = NO
    KEEP_ATTRS = _building_id
    -> GeometryPartExtractor_4
SurfaceSplitter_2
    FRONT -> SurfaceOnSurfaceOverlayer [SURFACE]
BoundsExtractor_2
    ZMAX = _zmax
    ZMIN = _zmin
    -> StatisticsCalculator
Note: GroundSurfaceの条件？
StatisticsCalculator
    CALCULATION_MODE = NUMERIC
    FEAT_STATS = _zmax,NUMERIC_MODE,,MAX,,,,,,,,,,,;_zmin,NUMERIC_MODE,MIN,,,,,,,,,,,,
    COMPLETE -> PlanarityFilter_3
Note: WallSurface / AttributeManager_2 : Input
Junction_28
    -> Junction_29
Note: IfcSlab (Wall) / TestFilter_2 : 鉛直
Junction_29
    -> AttributeManager_8
AttributeManager_9
    ATTR_TABLE:
      REMOVE Name
      REMOVE ifc_parent_unique_id
      REMOVE ifc_unique_id
      REMOVE _geometry_name
      REMOVE _surfaceNormalX
      REMOVE _surfaceNormalY
      REMOVE _surfaceNormalZ
      REMOVE _pointOnSurfaceX
      REMOVE _pointOnSurfaceY
      REMOVE _pointOnSurfaceZ
      SET_TO gml_id = face_@UUID()
      SET_TO citygml_lod_name = lod4MultiSurface
      REMOVE _parent_feature_type
      REMOVE _part_number
      REMOVE _overlaps
      REMOVE _zmin
      REMOVE _zmax
      REMOVE _zmax.max
      REMOVE _zmin.min
    -> Junction_31
    -> GeometryPropertySetter_7
GeometryPropertySetter_7
    GQUERY:
      for $geom in //geometry
      where $geom/count(parent::geometry) = 0
      return number($geom/@fme_id)
    OVERWRITE_CHOICE = Yes
    REMOVE_ATTRIBUTE = Yes
    SETTYPE_PARAM = Traits From Attributes
    SRC_ATTRS = citygml_lod_name gml_id
    SET -> AttributeCreator_14
AttributeCreator_14
    ATTR_TABLE:
      SET_TO gml_id = bdry_@UUID()
      SET_TO gml_parent_id = @Value(_building_id)
      SET_TO citygml_feature_role = boundedBy
    -> PLATEAU.IfcReprojector_8 [IfcFeature]
PLATEAU.IfcReprojector_8
    DEST_COORDSYS = $(DEST_COORDSYS)
    LENGTH_MULTIPLIER = @Value(_lengthmultiplier)
    REPROJECTION_PARAMS = @Value(_reprojection_params)
    Reprojected -> AttributeFilter
AttributeFilter
    ATTR_NAME = _citygml_feature_type
    ATTR_VALUES = RoofSurface,OuterFloorSurface,OuterCeilingSurface,GroundSurface,<Empty>,<Missing>,<Null>,<Unfiltered>
    RoofSurface -> RoofSurface (writer CITYGML_2)
    OuterFloorSurface -> OuterFloorSurface (writer CITYGML_2)
    OuterCeilingSurface -> OuterCeilingSurface (writer CITYGML_2)
    GroundSurface -> GroundSurface (writer CITYGML_2)
RoofSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, uro_ifc_boundary_surface_attribute{}.uro_ifc_building_uro_global_id xml_buffer, uro_ifc_boundary_surface_attribute{}.uro_ifc_building_uro_name xml_buffer, uro_ifc_boundary_surface_attribute{}.uro_ifc_building_uro_description xml_buffer, uro_ifc_boundary_surface_attribute{}.uro_ifc_building_uro_object_type xml_buffer, uro_ifc_boundary_surface_attribute{}.uro_ifc_building_uro_long_name xml_buffer, uro_ifc_boundary_surface_attribute{}.uro_ifc_building_uro_composition_type xml_char(7), uro_ifc_boundary_surface_attribute{}.uro_ifc_building_uro_elevation_of_ref_height xml_real64, uro_ifc_boundary_surface_attribute{}.uro_ifc_building_uro_elevation_of_ref_height_units xml_buffer, uro_ifc_boundary_surface_attribute{}.uro_ifc_building_uro_elevation_of_terrain xml_real64, uro_ifc_boundary_surface_attribute{}.uro_ifc_building_uro_elevation_of_terrain_units xml_buffer, uro_ifc_boundary_surface_attribute{}.uro_ifc_building_uro_building_address_xlink_href xml_buffer, uro_ifc_boundary_surface_attribute{}.uro_ifc_building_element_uro_global_id xml_buffer, uro_ifc_boundary_surface_attribute{}.uro_ifc_building_element_uro_name xml_buffer, uro_ifc_boundary_surface_attribute{}.uro_ifc_building_element_uro_description xml_buffer,
      uro_ifc_boundary_surface_attribute{}.uro_ifc_building_element_uro_object_type xml_buffer, uro_ifc_boundary_surface_attribute{}.uro_ifc_building_element_uro_tag xml_buffer, uro_ifc_boundary_surface_attribute{}.uro_ifc_building_element_uro_element_type xml_buffer, uro_ifc_boundary_surface_attribute{}.uro_ifc_building_element_uro_element_type_codeSpace xml_buffer, uro_ifc_boundary_surface_attribute{}.uro_ifc_building_element_uro_predefined_type xml_buffer, uro_ifc_boundary_surface_attribute{}.uro_ifc_building_element_uro_predefined_type_codeSpace xml_buffer, uro_ifc_boundary_surface_attribute{}.uro_ifc_building_element_uro_shape_type xml_buffer, uro_ifc_boundary_surface_attribute{}.uro_ifc_building_element_uro_shape_type_codeSpace xml_buffer, uro_ifc_boundary_surface_attribute{}.uro_ifc_building_element_uro_number_of_riser xml_int64, uro_ifc_boundary_surface_attribute{}.uro_ifc_building_element_uro_number_of_treads xml_int64, uro_ifc_boundary_surface_attribute{}.uro_ifc_building_element_uro_riser_height xml_int64, uro_ifc_boundary_surface_attribute{}.uro_ifc_building_element_uro_tread_length xml_int64, uro_ifc_boundary_surface_attribute{}.uro_ifc_building_element_uro_operation_type xml_char(11), uro_ifc_boundary_surface_attribute{}.uro_ifc_building_element_uro_capacity_by_weight xml_real64, uro_ifc_boundary_surface_attribute{}.uro_ifc_building_element_uro_capacity_by_weight_units xml_buffer, uro_ifc_boundary_surface_attribute{}.uro_ifc_building_element_uro_capacity_by_number xml_int64, uro_ifc_boundary_surface_attribute{}.uro_ifc_building_storey_uro_global_id xml_buffer, uro_ifc_boundary_surface_attribute{}.uro_ifc_building_storey_uro_name xml_buffer, uro_ifc_boundary_surface_attribute{}.uro_ifc_building_storey_uro_description xml_buffer, uro_ifc_boundary_surface_attribute{}.uro_ifc_building_storey_uro_object_type xml_buffer, uro_ifc_boundary_surface_attribute{}.uro_ifc_building_storey_uro_long_name xml_buffer, uro_ifc_boundary_surface_attribute{}.uro_ifc_building_storey_uro_composition_type xml_char(7), uro_ifc_boundary_surface_attribute{}.uro_ifc_building_storey_uro_elevation xml_real64, uro_ifc_boundary_surface_attribute{}.uro_ifc_building_storey_uro_elevation_units xml_buffer, uro_ifc_boundary_surface_attribute{}.uro_ifc_classification_reference_uro_location xml_buffer, uro_ifc_boundary_surface_attribute{}.uro_ifc_classification_reference_uro_item_reference xml_buffer, uro_ifc_boundary_surface_attribute{}.uro_ifc_classification_reference_uro_item_reference_codeSpace xml_buffer, uro_ifc_boundary_surface_attribute{}.uro_ifc_classification_reference_uro_name xml_buffer, uro_ifc_boundary_surface_attribute{}.uro_ifc_classification_reference_uro_name_codeSpace xml_buffer, uro_ifc_boundary_surface_attribute{}.uro_ifc_classification_reference_uro_reference_source_uro_ifc_classification_uro_source xml_buffer,
      uro_ifc_boundary_surface_attribute{}.uro_ifc_classification_reference_uro_reference_source_uro_ifc_classification_uro_edition xml_buffer, uro_ifc_boundary_surface_attribute{}.uro_ifc_classification_reference_uro_reference_source_uro_ifc_classification_uro_edition_date xml_date, uro_ifc_boundary_surface_attribute{}.uro_ifc_classification_reference_uro_reference_source_uro_ifc_classification_uro_name xml_buffer, uro_ifc_boundary_surface_attribute{}.uro_ifc_coordinate_reference_system_uro_name xml_buffer, uro_ifc_boundary_surface_attribute{}.uro_ifc_coordinate_reference_system_uro_description xml_buffer, uro_ifc_boundary_surface_attribute{}.uro_ifc_coordinate_reference_system_uro_geodetic_datum xml_buffer, uro_ifc_boundary_surface_attribute{}.uro_ifc_coordinate_reference_system_uro_vertical_datum xml_buffer, uro_ifc_boundary_surface_attribute{}.uro_ifc_curtain_wall_uro_global_id xml_buffer, uro_ifc_boundary_surface_attribute{}.uro_ifc_curtain_wall_uro_name xml_buffer, uro_ifc_boundary_surface_attribute{}.uro_ifc_curtain_wall_uro_description xml_buffer, uro_ifc_boundary_surface_attribute{}.uro_ifc_curtain_wall_uro_object_type xml_buffer, uro_ifc_boundary_surface_attribute{}.uro_ifc_curtain_wall_uro_tag xml_buffer, uro_ifc_boundary_surface_attribute{}.uro_ifc_curtain_wall_uro_element_type xml_buffer, uro_ifc_boundary_surface_attribute{}.uro_ifc_curtain_wall_uro_element_type_codeSpace xml_buffer, uro_ifc_boundary_surface_attribute{}.uro_ifc_curtain_wall_uro_predefined_type xml_buffer, uro_ifc_boundary_surface_attribute{}.uro_ifc_curtain_wall_uro_predefined_type_codeSpace xml_buffer, uro_ifc_boundary_surface_attribute{}.uro_ifc_curtain_wall_uro_shape_type xml_buffer, uro_ifc_boundary_surface_attribute{}.uro_ifc_curtain_wall_uro_shape_type_codeSpace xml_buffer, uro_ifc_boundary_surface_attribute{}.uro_ifc_curtain_wall_uro_number_of_riser xml_int64, uro_ifc_boundary_surface_attribute{}.uro_ifc_curtain_wall_uro_number_of_treads xml_int64, uro_ifc_boundary_surface_attribute{}.uro_ifc_curtain_wall_uro_riser_height xml_int64, uro_ifc_boundary_surface_attribute{}.uro_ifc_curtain_wall_uro_tread_length xml_int64, uro_ifc_boundary_surface_attribute{}.uro_ifc_curtain_wall_uro_operation_type xml_char(11), uro_ifc_boundary_surface_attribute{}.uro_ifc_curtain_wall_uro_capacity_by_weight xml_real64, uro_ifc_boundary_surface_attribute{}.uro_ifc_curtain_wall_uro_capacity_by_weight_units xml_buffer, uro_ifc_boundary_surface_attribute{}.uro_ifc_curtain_wall_uro_capacity_by_number xml_int64, uro_ifc_boundary_surface_attribute{}.uro_ifc_door_uro_global_id xml_buffer, uro_ifc_boundary_surface_attribute{}.uro_ifc_door_uro_name xml_buffer, uro_ifc_boundary_surface_attribute{}.uro_ifc_door_uro_description xml_buffer, uro_ifc_boundary_surface_attribute{}.uro_ifc_door_uro_object_type xml_buffer,
      uro_ifc_boundary_surface_attribute{}.uro_ifc_door_uro_tag xml_buffer, uro_ifc_boundary_surface_attribute{}.uro_ifc_door_uro_element_type xml_buffer, uro_ifc_boundary_surface_attribute{}.uro_ifc_door_uro_element_type_codeSpace xml_buffer, uro_ifc_boundary_surface_attribute{}.uro_ifc_door_uro_predefined_type xml_buffer, uro_ifc_boundary_surface_attribute{}.uro_ifc_door_uro_predefined_type_codeSpace xml_buffer, uro_ifc_boundary_surface_attribute{}.uro_ifc_door_uro_shape_type xml_buffer, uro_ifc_boundary_surface_attribute{}.uro_ifc_door_uro_shape_type_codeSpace xml_buffer, uro_ifc_boundary_surface_attribute{}.uro_ifc_door_uro_number_of_riser xml_int64, uro_ifc_boundary_surface_attribute{}.uro_ifc_door_uro_number_of_treads xml_int64, uro_ifc_boundary_surface_attribute{}.uro_ifc_door_uro_riser_height xml_int64, uro_ifc_boundary_surface_attribute{}.uro_ifc_door_uro_tread_length xml_int64, uro_ifc_boundary_surface_attribute{}.uro_ifc_door_uro_operation_type xml_char(11), uro_ifc_boundary_surface_attribute{}.uro_ifc_door_uro_capacity_by_weight xml_real64, uro_ifc_boundary_surface_attribute{}.uro_ifc_door_uro_capacity_by_weight_units xml_buffer, uro_ifc_boundary_surface_attribute{}.uro_ifc_door_uro_capacity_by_number xml_int64, uro_ifc_boundary_surface_attribute{}.uro_ifc_door_uro_overall_height xml_real64, uro_ifc_boundary_surface_attribute{}.uro_ifc_door_uro_overall_height_units xml_buffer, uro_ifc_boundary_surface_attribute{}.uro_ifc_door_uro_overall_width xml_real64, uro_ifc_boundary_surface_attribute{}.uro_ifc_door_uro_overall_width_units xml_buffer, uro_ifc_boundary_surface_attribute{}.uro_ifc_furnishing_element_uro_global_id xml_buffer, uro_ifc_boundary_surface_attribute{}.uro_ifc_furnishing_element_uro_name xml_buffer, uro_ifc_boundary_surface_attribute{}.uro_ifc_furnishing_element_uro_description xml_buffer, uro_ifc_boundary_surface_attribute{}.uro_ifc_furnishing_element_uro_object_type xml_buffer, uro_ifc_boundary_surface_attribute{}.uro_ifc_furnishing_element_uro_tag xml_buffer, uro_ifc_boundary_surface_attribute{}.uro_ifc_map_conversion_uro_source_crs_uro_crs_uro_ifc_projected_crs_uro_name xml_buffer, uro_ifc_boundary_surface_attribute{}.uro_ifc_map_conversion_uro_source_crs_uro_crs_uro_ifc_projected_crs_uro_description xml_buffer, uro_ifc_boundary_surface_attribute{}.uro_ifc_map_conversion_uro_source_crs_uro_crs_uro_ifc_projected_crs_uro_geodetic_datum xml_buffer, uro_ifc_boundary_surface_attribute{}.uro_ifc_map_conversion_uro_source_crs_uro_crs_uro_ifc_projected_crs_uro_vertical_datum xml_buffer, uro_ifc_boundary_surface_attribute{}.uro_ifc_map_conversion_uro_source_crs_uro_crs_uro_ifc_projected_crs_uro_map_unit xml_buffer, uro_ifc_boundary_surface_attribute{}.uro_ifc_map_conversion_uro_source_crs_uro_crs_uro_ifc_projected_crs_uro_map_projection xml_buffer,
      uro_ifc_boundary_surface_attribute{}.uro_ifc_map_conversion_uro_source_crs_uro_crs_uro_ifc_projected_crs_uro_map_zone xml_buffer, uro_ifc_boundary_surface_attribute{}.uro_ifc_map_conversion_uro_source_crs_uro_crs_uro_ifc_coordinate_reference_system_uro_name xml_buffer, uro_ifc_boundary_surface_attribute{}.uro_ifc_map_conversion_uro_source_crs_uro_crs_uro_ifc_coordinate_reference_system_uro_description xml_buffer, uro_ifc_boundary_surface_attribute{}.uro_ifc_map_conversion_uro_source_crs_uro_crs_uro_ifc_coordinate_reference_system_uro_geodetic_datum xml_buffer, uro_ifc_boundary_surface_attribute{}.uro_ifc_map_conversion_uro_source_crs_uro_crs_uro_ifc_coordinate_reference_system_uro_vertical_datum xml_buffer, uro_ifc_boundary_surface_attribute{}.uro_ifc_map_conversion_uro_source_crs_uro_context_uro_ifc_geometric_representation_context_uro_context_identifier xml_buffer, uro_ifc_boundary_surface_attribute{}.uro_ifc_map_conversion_uro_source_crs_uro_context_uro_ifc_geometric_representation_context_uro_context_type xml_buffer, uro_ifc_boundary_surface_attribute{}.uro_ifc_map_conversion_uro_source_crs_uro_context_uro_ifc_geometric_representation_context_uro_coordinate_space_dimension xml_int64, uro_ifc_boundary_surface_attribute{}.uro_ifc_map_conversion_uro_source_crs_uro_context_uro_ifc_geometric_representation_context_uro_precision xml_real64, uro_ifc_boundary_surface_attribute{}.uro_ifc_map_conversion_uro_source_crs_uro_context_uro_ifc_geometric_representation_context_uro_true_north xml_real64, uro_ifc_boundary_surface_attribute{}.uro_ifc_map_conversion_uro_target_crs_uro_ifc_projected_crs_uro_name xml_buffer, uro_ifc_boundary_surface_attribute{}.uro_ifc_map_conversion_uro_target_crs_uro_ifc_projected_crs_uro_description xml_buffer, uro_ifc_boundary_surface_attribute{}.uro_ifc_map_conversion_uro_target_crs_uro_ifc_projected_crs_uro_geodetic_datum xml_buffer, uro_ifc_boundary_surface_attribute{}.uro_ifc_map_conversion_uro_target_crs_uro_ifc_projected_crs_uro_vertical_datum xml_buffer, uro_ifc_boundary_surface_attribute{}.uro_ifc_map_conversion_uro_target_crs_uro_ifc_projected_crs_uro_map_unit xml_buffer, uro_ifc_boundary_surface_attribute{}.uro_ifc_map_conversion_uro_target_crs_uro_ifc_projected_crs_uro_map_projection xml_buffer, uro_ifc_boundary_surface_attribute{}.uro_ifc_map_conversion_uro_target_crs_uro_ifc_projected_crs_uro_map_zone xml_buffer, uro_ifc_boundary_surface_attribute{}.uro_ifc_map_conversion_uro_target_crs_uro_ifc_coordinate_reference_system_uro_name xml_buffer, uro_ifc_boundary_surface_attribute{}.uro_ifc_map_conversion_uro_target_crs_uro_ifc_coordinate_reference_system_uro_description xml_buffer, uro_ifc_boundary_surface_attribute{}.uro_ifc_map_conversion_uro_target_crs_uro_ifc_coordinate_reference_system_uro_geodetic_datum xml_buffer, uro_ifc_boundary_surface_attribute{}.uro_ifc_map_conversion_uro_target_crs_uro_ifc_coordinate_reference_system_uro_vertical_datum xml_buffer, uro_ifc_boundary_surface_attribute{}.uro_ifc_map_conversion_uro_eastings xml_buffer, uro_ifc_boundary_surface_attribute{}.uro_ifc_map_conversion_uro_northings xml_buffer, uro_ifc_boundary_surface_attribute{}.uro_ifc_map_conversion_uro_orthogonal_height xml_real64, uro_ifc_boundary_surface_attribute{}.uro_ifc_map_conversion_uro_orthogonal_height_units xml_buffer, uro_ifc_boundary_surface_attribute{}.uro_ifc_map_conversion_uro_x_axis_abscissa xml_real64, uro_ifc_boundary_surface_attribute{}.uro_ifc_map_conversion_uro_x_axis_ordinate xml_real64, uro_ifc_boundary_surface_attribute{}.uro_ifc_map_conversion_uro_scale xml_real64, uro_ifc_boundary_surface_attribute{}.uro_ifc_opening_element_uro_global_id xml_buffer, uro_ifc_boundary_surface_attribute{}.uro_ifc_opening_element_uro_name xml_buffer,
      uro_ifc_boundary_surface_attribute{}.uro_ifc_opening_element_uro_description xml_buffer, uro_ifc_boundary_surface_attribute{}.uro_ifc_opening_element_uro_object_type xml_buffer, uro_ifc_boundary_surface_attribute{}.uro_ifc_opening_element_uro_tag xml_buffer, uro_ifc_boundary_surface_attribute{}.uro_ifc_opening_element_uro_nominal_area xml_real64, uro_ifc_boundary_surface_attribute{}.uro_ifc_opening_element_uro_nominal_area_units xml_buffer, uro_ifc_boundary_surface_attribute{}.uro_ifc_opening_element_uro_nominal_volume xml_real64, uro_ifc_boundary_surface_attribute{}.uro_ifc_opening_element_uro_nominal_volume_units xml_buffer, uro_ifc_boundary_surface_attribute{}.uro_ifc_project_uro_global_id xml_buffer, uro_ifc_boundary_surface_attribute{}.uro_ifc_project_uro_name xml_buffer, uro_ifc_boundary_surface_attribute{}.uro_ifc_project_uro_description xml_buffer, uro_ifc_boundary_surface_attribute{}.uro_ifc_project_uro_object_type xml_buffer, uro_ifc_boundary_surface_attribute{}.uro_ifc_project_uro_long_name xml_buffer, uro_ifc_boundary_surface_attribute{}.uro_ifc_project_uro_phase xml_buffer, uro_ifc_boundary_surface_attribute{}.uro_ifc_project_uro_representation_contexts_uro_ifc_geometric_representation_context_uro_context_identifier xml_buffer, uro_ifc_boundary_surface_attribute{}.uro_ifc_project_uro_representation_contexts_uro_ifc_geometric_representation_context_uro_context_type xml_buffer, uro_ifc_boundary_surface_attribute{}.uro_ifc_project_uro_representation_contexts_uro_ifc_geometric_representation_context_uro_coordinate_space_dimension xml_int64, uro_ifc_boundary_surface_attribute{}.uro_ifc_project_uro_representation_contexts_uro_ifc_geometric_representation_context_uro_precision xml_real64, uro_ifc_boundary_surface_attribute{}.uro_ifc_project_uro_representation_contexts_uro_ifc_geometric_representation_context_uro_true_north xml_real64, uro_ifc_boundary_surface_attribute{}.uro_ifc_project_uro_units_in_context{}.uro_ifc_unit_uro_dimensions xml_int64, uro_ifc_boundary_surface_attribute{}.uro_ifc_project_uro_units_in_context{}.uro_ifc_unit_uro_unit_type xml_char(28), uro_ifc_boundary_surface_attribute{}.uro_ifc_project_uro_units_in_context{}.uro_ifc_unit_uro_perfix xml_buffer, uro_ifc_boundary_surface_attribute{}.uro_ifc_project_uro_units_in_context{}.uro_ifc_unit_uro_name xml_buffer, uro_ifc_boundary_surface_attribute{}.uro_ifc_projected_crs_uro_name xml_buffer, uro_ifc_boundary_surface_attribute{}.uro_ifc_projected_crs_uro_description xml_buffer, uro_ifc_boundary_surface_attribute{}.uro_ifc_projected_crs_uro_geodetic_datum xml_buffer, uro_ifc_boundary_surface_attribute{}.uro_ifc_projected_crs_uro_vertical_datum xml_buffer, uro_ifc_boundary_surface_attribute{}.uro_ifc_projected_crs_uro_map_unit xml_buffer, uro_ifc_boundary_surface_attribute{}.uro_ifc_projected_crs_uro_map_projection xml_buffer, uro_ifc_boundary_surface_attribute{}.uro_ifc_projected_crs_uro_map_zone xml_buffer, uro_ifc_boundary_surface_attribute{}.uro_ifc_pset_building_common_uro_building_id xml_real64,
      uro_ifc_boundary_surface_attribute{}.uro_ifc_pset_building_common_uro_building_id_units xml_buffer, uro_ifc_boundary_surface_attribute{}.uro_ifc_pset_building_common_uro_is_permanent_id xml_real64, uro_ifc_boundary_surface_attribute{}.uro_ifc_pset_building_common_uro_is_permanent_id_units xml_buffer, uro_ifc_boundary_surface_attribute{}.uro_ifc_pset_building_common_uro_main_fire_use xml_buffer, uro_ifc_boundary_surface_attribute{}.uro_ifc_pset_building_common_uro_ancillary_fire_use xml_buffer, uro_ifc_boundary_surface_attribute{}.uro_ifc_pset_building_common_uro_sprinkler_protection xml_boolean, uro_ifc_boundary_surface_attribute{}.uro_ifc_pset_building_common_uro_sprinkler_protection_automatic xml_boolean, uro_ifc_boundary_surface_attribute{}.uro_ifc_pset_building_common_uro_occupancy_type xml_buffer, uro_ifc_boundary_surface_attribute{}.uro_ifc_pset_building_common_uro_occupancy_type_codeSpace xml_buffer, uro_ifc_boundary_surface_attribute{}.uro_ifc_pset_building_common_uro_gross_planned_area xml_real64, uro_ifc_boundary_surface_attribute{}.uro_ifc_pset_building_common_uro_gross_planned_area_units xml_buffer, uro_ifc_boundary_surface_attribute{}.uro_ifc_pset_building_common_uro_number_of_storeys xml_int64, uro_ifc_boundary_surface_attribute{}.uro_ifc_pset_building_common_uro_year_of_construction xml_buffer, uro_ifc_boundary_surface_attribute{}.uro_ifc_pset_building_common_uro_is_landmarked xml_boolean, uro_ifc_boundary_surface_attribute{}.uro_ifc_pset_door_common_uro_reference xml_buffer, uro_ifc_boundary_surface_attribute{}.uro_ifc_pset_door_common_uro_acoustic_rating xml_buffer, uro_ifc_boundary_surface_attribute{}.uro_ifc_pset_door_common_uro_firerating xml_buffer, uro_ifc_boundary_surface_attribute{}.uro_ifc_pset_door_common_uro_security_rating xml_buffer, uro_ifc_boundary_surface_attribute{}.uro_ifc_pset_door_common_uro_is_external xml_boolean, uro_ifc_boundary_surface_attribute{}.uro_ifc_pset_door_common_uro_infiltration xml_real64, uro_ifc_boundary_surface_attribute{}.uro_ifc_pset_door_common_uro_thermal_transmittance xml_real64, uro_ifc_boundary_surface_attribute{}.uro_ifc_pset_door_common_uro_glazing_area_fraction xml_real64, uro_ifc_boundary_surface_attribute{}.uro_ifc_pset_door_common_uro_handicap_accessible xml_real64, uro_ifc_boundary_surface_attribute{}.uro_ifc_pset_door_common_uro_fire_exit xml_boolean, uro_ifc_boundary_surface_attribute{}.uro_ifc_pset_door_common_uro_self_closing xml_real64, uro_ifc_boundary_surface_attribute{}.uro_ifc_pset_door_common_uro_smoke_stop xml_boolean, uro_ifc_boundary_surface_attribute{}.uro_ifc_pset_opening_element_common_uro_reference xml_buffer, uro_ifc_boundary_surface_attribute{}.uro_ifc_pset_opening_element_common_uro_purpose xml_buffer, uro_ifc_boundary_surface_attribute{}.uro_ifc_pset_opening_element_common_uro_fire_exit xml_boolean, uro_ifc_boundary_surface_attribute{}.uro_ifc_pset_opening_element_common_uro_protected_opening xml_boolean,
      uro_ifc_boundary_surface_attribute{}.uro_ifc_pset_opening_element_common_uro_parallel_jambs xml_boolean, uro_ifc_boundary_surface_attribute{}.uro_ifc_pset_site_common_uro_buildable_area xml_real64, uro_ifc_boundary_surface_attribute{}.uro_ifc_pset_site_common_uro_buildable_area_units xml_buffer, uro_ifc_boundary_surface_attribute{}.uro_ifc_pset_site_common_uro_total_area xml_real64, uro_ifc_boundary_surface_attribute{}.uro_ifc_pset_site_common_uro_total_area_units xml_buffer, uro_ifc_boundary_surface_attribute{}.uro_ifc_pset_site_common_uro_building_height_limit xml_real64, uro_ifc_boundary_surface_attribute{}.uro_ifc_pset_site_common_uro_building_height_limit_units xml_buffer, uro_ifc_boundary_surface_attribute{}.uro_ifc_pset_space_common_uro_reference xml_buffer, uro_ifc_boundary_surface_attribute{}.uro_ifc_pset_space_common_uro_category xml_buffer, uro_ifc_boundary_surface_attribute{}.uro_ifc_pset_space_common_uro_category_codeSpace xml_buffer, uro_ifc_boundary_surface_attribute{}.uro_ifc_pset_space_common_uro_floor_covering xml_buffer, uro_ifc_boundary_surface_attribute{}.uro_ifc_pset_space_common_uro_wall_covering xml_buffer, uro_ifc_boundary_surface_attribute{}.uro_ifc_pset_space_common_uro_ceiling_covering xml_buffer, uro_ifc_boundary_surface_attribute{}.uro_ifc_pset_space_common_uro_skirting_covering xml_buffer, uro_ifc_boundary_surface_attribute{}.uro_ifc_pset_space_common_uro_gross_planned_area xml_real64, uro_ifc_boundary_surface_attribute{}.uro_ifc_pset_space_common_uro_gross_planned_area_units xml_buffer, uro_ifc_boundary_surface_attribute{}.uro_ifc_pset_space_common_uro_net_planned_area xml_real64, uro_ifc_boundary_surface_attribute{}.uro_ifc_pset_space_common_uro_net_planned_area_units xml_buffer, uro_ifc_boundary_surface_attribute{}.uro_ifc_pset_space_common_uro_publicly_accessible xml_boolean, uro_ifc_boundary_surface_attribute{}.uro_ifc_pset_space_common_uro_handicap_accessible xml_boolean, uro_ifc_boundary_surface_attribute{}.uro_ifc_pset_space_common_uro_concealed_flooring xml_boolean, uro_ifc_boundary_surface_attribute{}.uro_ifc_pset_space_common_uro_concealed_ceiling xml_boolean, uro_ifc_boundary_surface_attribute{}.uro_ifc_pset_window_common_uro_reference xml_buffer, uro_ifc_boundary_surface_attribute{}.uro_ifc_pset_window_common_uro_acoustic_rating xml_buffer, uro_ifc_boundary_surface_attribute{}.uro_ifc_pset_window_common_uro_firerating xml_buffer, uro_ifc_boundary_surface_attribute{}.uro_ifc_pset_window_common_uro_security_rating xml_buffer, uro_ifc_boundary_surface_attribute{}.uro_ifc_pset_window_common_uro_is_external xml_boolean, uro_ifc_boundary_surface_attribute{}.uro_ifc_pset_window_common_uro_infiltration xml_real64, uro_ifc_boundary_surface_attribute{}.uro_ifc_pset_window_common_uro_thermal_transmittance xml_real64, uro_ifc_boundary_surface_attribute{}.uro_ifc_pset_window_common_uro_glazing_area_fraction xml_real64,
      uro_ifc_boundary_surface_attribute{}.uro_ifc_pset_window_common_uro_smoke_stop xml_boolean, uro_ifc_boundary_surface_attribute{}.uro_ifc_site_uro_global_id xml_buffer, uro_ifc_boundary_surface_attribute{}.uro_ifc_site_uro_name xml_buffer, uro_ifc_boundary_surface_attribute{}.uro_ifc_site_uro_description xml_buffer, uro_ifc_boundary_surface_attribute{}.uro_ifc_site_uro_object_type xml_buffer, uro_ifc_boundary_surface_attribute{}.uro_ifc_site_uro_long_name xml_buffer, uro_ifc_boundary_surface_attribute{}.uro_ifc_site_uro_composition_type xml_char(7), uro_ifc_boundary_surface_attribute{}.uro_ifc_site_uro_ref_longitude xml_real64, uro_ifc_boundary_surface_attribute{}.uro_ifc_site_uro_ref_latitude xml_real64, uro_ifc_boundary_surface_attribute{}.uro_ifc_site_uro_ref_elevation xml_real64, uro_ifc_boundary_surface_attribute{}.uro_ifc_site_uro_ref_elevation_units xml_buffer, uro_ifc_boundary_surface_attribute{}.uro_ifc_site_uro_land_title_number xml_buffer, uro_ifc_boundary_surface_attribute{}.uro_ifc_site_uro_site_address_xlink_href xml_buffer, uro_ifc_boundary_surface_attribute{}.uro_ifc_space_uro_global_id xml_buffer, uro_ifc_boundary_surface_attribute{}.uro_ifc_space_uro_name xml_buffer, uro_ifc_boundary_surface_attribute{}.uro_ifc_space_uro_description xml_buffer, uro_ifc_boundary_surface_attribute{}.uro_ifc_space_uro_object_type xml_buffer, uro_ifc_boundary_surface_attribute{}.uro_ifc_space_uro_long_name xml_buffer, uro_ifc_boundary_surface_attribute{}.uro_ifc_space_uro_composition_type xml_char(7), uro_ifc_boundary_surface_attribute{}.uro_ifc_space_uro_interioror_exterior_space xml_char(10), uro_ifc_boundary_surface_attribute{}.uro_ifc_space_uro_elevation_with_flooring xml_real64, uro_ifc_boundary_surface_attribute{}.uro_ifc_space_uro_elevation_with_flooring_units xml_buffer, uro_ifc_boundary_surface_attribute{}.uro_ifc_space_base_quantity_uro_nominal_height xml_real64, uro_ifc_boundary_surface_attribute{}.uro_ifc_space_base_quantity_uro_nominal_height_units xml_buffer, uro_ifc_boundary_surface_attribute{}.uro_ifc_space_base_quantity_uro_clear_height xml_real64, uro_ifc_boundary_surface_attribute{}.uro_ifc_space_base_quantity_uro_clear_height_units xml_buffer, uro_ifc_boundary_surface_attribute{}.uro_ifc_space_base_quantity_uro_finish_ceiling_height xml_real64, uro_ifc_boundary_surface_attribute{}.uro_ifc_space_base_quantity_uro_finish_ceiling_height_units xml_buffer, uro_ifc_boundary_surface_attribute{}.uro_ifc_space_base_quantity_uro_gross_perimeter xml_real64, uro_ifc_boundary_surface_attribute{}.uro_ifc_space_base_quantity_uro_gross_perimeter_units xml_buffer,
      uro_ifc_boundary_surface_attribute{}.uro_ifc_space_base_quantity_uro_net_perimeter xml_real64, uro_ifc_boundary_surface_attribute{}.uro_ifc_space_base_quantity_uro_net_perimeter_units xml_buffer, uro_ifc_boundary_surface_attribute{}.uro_ifc_space_base_quantity_uro_gross_ceiling_area xml_real64, uro_ifc_boundary_surface_attribute{}.uro_ifc_space_base_quantity_uro_gross_ceiling_area_units xml_buffer, uro_ifc_boundary_surface_attribute{}.uro_ifc_space_base_quantity_uro_gross_floor_area xml_real64, uro_ifc_boundary_surface_attribute{}.uro_ifc_space_base_quantity_uro_gross_floor_area_units xml_buffer, uro_ifc_boundary_surface_attribute{}.uro_ifc_space_base_quantity_uro_net_ceiling_area xml_real64, uro_ifc_boundary_surface_attribute{}.uro_ifc_space_base_quantity_uro_net_ceiling_area_units xml_buffer, uro_ifc_boundary_surface_attribute{}.uro_ifc_space_base_quantity_uro_net_floor_area xml_real64, uro_ifc_boundary_surface_attribute{}.uro_ifc_space_base_quantity_uro_net_floor_area_units xml_buffer, uro_ifc_boundary_surface_attribute{}.uro_ifc_space_base_quantity_uro_gross_wall_area xml_real64, uro_ifc_boundary_surface_attribute{}.uro_ifc_space_base_quantity_uro_gross_wall_area_units xml_buffer, uro_ifc_boundary_surface_attribute{}.uro_ifc_space_base_quantity_uro_net_wall_area xml_real64, uro_ifc_boundary_surface_attribute{}.uro_ifc_space_base_quantity_uro_net_wall_area_units xml_buffer, uro_ifc_boundary_surface_attribute{}.uro_ifc_space_base_quantity_uro_gross_volume xml_real64, uro_ifc_boundary_surface_attribute{}.uro_ifc_space_base_quantity_uro_gross_volume_units xml_buffer, uro_ifc_boundary_surface_attribute{}.uro_ifc_space_base_quantity_uro_net_volume xml_real64, uro_ifc_boundary_surface_attribute{}.uro_ifc_space_base_quantity_uro_net_volume_units xml_buffer, uro_ifc_boundary_surface_attribute{}.uro_ifc_wall_uro_global_id xml_buffer, uro_ifc_boundary_surface_attribute{}.uro_ifc_wall_uro_name xml_buffer, uro_ifc_boundary_surface_attribute{}.uro_ifc_wall_uro_description xml_buffer, uro_ifc_boundary_surface_attribute{}.uro_ifc_wall_uro_object_type xml_buffer, uro_ifc_boundary_surface_attribute{}.uro_ifc_wall_uro_tag xml_buffer, uro_ifc_boundary_surface_attribute{}.uro_ifc_wall_uro_element_type xml_buffer, uro_ifc_boundary_surface_attribute{}.uro_ifc_wall_uro_element_type_codeSpace xml_buffer, uro_ifc_boundary_surface_attribute{}.uro_ifc_wall_uro_predefined_type xml_buffer, uro_ifc_boundary_surface_attribute{}.uro_ifc_wall_uro_predefined_type_codeSpace xml_buffer, uro_ifc_boundary_surface_attribute{}.uro_ifc_wall_uro_shape_type xml_buffer, uro_ifc_boundary_surface_attribute{}.uro_ifc_wall_uro_shape_type_codeSpace xml_buffer, uro_ifc_boundary_surface_attribute{}.uro_ifc_wall_uro_number_of_riser xml_int64,
      uro_ifc_boundary_surface_attribute{}.uro_ifc_wall_uro_number_of_treads xml_int64, uro_ifc_boundary_surface_attribute{}.uro_ifc_wall_uro_riser_height xml_int64, uro_ifc_boundary_surface_attribute{}.uro_ifc_wall_uro_tread_length xml_int64, uro_ifc_boundary_surface_attribute{}.uro_ifc_wall_uro_operation_type xml_char(11), uro_ifc_boundary_surface_attribute{}.uro_ifc_wall_uro_capacity_by_weight xml_real64, uro_ifc_boundary_surface_attribute{}.uro_ifc_wall_uro_capacity_by_weight_units xml_buffer, uro_ifc_boundary_surface_attribute{}.uro_ifc_wall_uro_capacity_by_number xml_int64, uro_ifc_boundary_surface_attribute{}.uro_ifc_wall_uro_nominal_length xml_real64, uro_ifc_boundary_surface_attribute{}.uro_ifc_wall_uro_nominal_length_units xml_buffer, uro_ifc_boundary_surface_attribute{}.uro_ifc_wall_uro_nominal_width xml_real64, uro_ifc_boundary_surface_attribute{}.uro_ifc_wall_uro_nominal_width_units xml_buffer, uro_ifc_boundary_surface_attribute{}.uro_ifc_wall_uro_nominal_height xml_real64, uro_ifc_boundary_surface_attribute{}.uro_ifc_wall_uro_nominal_height_units xml_buffer, uro_ifc_boundary_surface_attribute{}.uro_ifc_wall_uro_gross_foot_print_area xml_real64, uro_ifc_boundary_surface_attribute{}.uro_ifc_wall_uro_gross_foot_print_area_units xml_buffer, uro_ifc_boundary_surface_attribute{}.uro_ifc_wall_uro_net_foot_print_area xml_real64, uro_ifc_boundary_surface_attribute{}.uro_ifc_wall_uro_net_foot_print_area_units xml_buffer, uro_ifc_boundary_surface_attribute{}.uro_ifc_wall_uro_gross_side_area xml_real64, uro_ifc_boundary_surface_attribute{}.uro_ifc_wall_uro_gross_side_area_units xml_buffer, uro_ifc_boundary_surface_attribute{}.uro_ifc_wall_uro_net_side_area xml_real64, uro_ifc_boundary_surface_attribute{}.uro_ifc_wall_uro_net_side_area_units xml_buffer, uro_ifc_boundary_surface_attribute{}.uro_ifc_wall_uro_gross_side_area_left xml_real64, uro_ifc_boundary_surface_attribute{}.uro_ifc_wall_uro_gross_side_area_left_units xml_buffer, uro_ifc_boundary_surface_attribute{}.uro_ifc_wall_uro_net_side_area_left xml_real64, uro_ifc_boundary_surface_attribute{}.uro_ifc_wall_uro_net_side_area_left_units xml_buffer, uro_ifc_boundary_surface_attribute{}.uro_ifc_wall_uro_gross_side_area_right xml_real64, uro_ifc_boundary_surface_attribute{}.uro_ifc_wall_uro_gross_side_area_right_units xml_buffer, uro_ifc_boundary_surface_attribute{}.uro_ifc_wall_uro_net_side_area_right xml_real64, uro_ifc_boundary_surface_attribute{}.uro_ifc_wall_uro_net_side_area_right_units xml_buffer, uro_ifc_boundary_surface_attribute{}.uro_ifc_wall_uro_gross_volume xml_real64,
      uro_ifc_boundary_surface_attribute{}.uro_ifc_wall_uro_gross_volume_units xml_buffer, uro_ifc_boundary_surface_attribute{}.uro_ifc_wall_uro_net_volume xml_real64, uro_ifc_boundary_surface_attribute{}.uro_ifc_wall_uro_net_volume_units xml_buffer, uro_ifc_boundary_surface_attribute{}.uro_ifc_wall_standard_case_uro_global_id xml_buffer, uro_ifc_boundary_surface_attribute{}.uro_ifc_wall_standard_case_uro_name xml_buffer, uro_ifc_boundary_surface_attribute{}.uro_ifc_wall_standard_case_uro_description xml_buffer, uro_ifc_boundary_surface_attribute{}.uro_ifc_wall_standard_case_uro_object_type xml_buffer, uro_ifc_boundary_surface_attribute{}.uro_ifc_wall_standard_case_uro_tag xml_buffer, uro_ifc_boundary_surface_attribute{}.uro_ifc_wall_standard_case_uro_element_type xml_buffer, uro_ifc_boundary_surface_attribute{}.uro_ifc_wall_standard_case_uro_element_type_codeSpace xml_buffer, uro_ifc_boundary_surface_attribute{}.uro_ifc_wall_standard_case_uro_predefined_type xml_buffer, uro_ifc_boundary_surface_attribute{}.uro_ifc_wall_standard_case_uro_predefined_type_codeSpace xml_buffer, uro_ifc_boundary_surface_attribute{}.uro_ifc_wall_standard_case_uro_shape_type xml_buffer, uro_ifc_boundary_surface_attribute{}.uro_ifc_wall_standard_case_uro_shape_type_codeSpace xml_buffer, uro_ifc_boundary_surface_attribute{}.uro_ifc_wall_standard_case_uro_number_of_riser xml_int64, uro_ifc_boundary_surface_attribute{}.uro_ifc_wall_standard_case_uro_number_of_treads xml_int64, uro_ifc_boundary_surface_attribute{}.uro_ifc_wall_standard_case_uro_riser_height xml_int64, uro_ifc_boundary_surface_attribute{}.uro_ifc_wall_standard_case_uro_tread_length xml_int64, uro_ifc_boundary_surface_attribute{}.uro_ifc_wall_standard_case_uro_operation_type xml_char(11), uro_ifc_boundary_surface_attribute{}.uro_ifc_wall_standard_case_uro_capacity_by_weight xml_real64, uro_ifc_boundary_surface_attribute{}.uro_ifc_wall_standard_case_uro_capacity_by_weight_units xml_buffer, uro_ifc_boundary_surface_attribute{}.uro_ifc_wall_standard_case_uro_capacity_by_number xml_int64, uro_ifc_boundary_surface_attribute{}.uro_ifc_wall_standard_case_uro_nominal_length xml_real64, uro_ifc_boundary_surface_attribute{}.uro_ifc_wall_standard_case_uro_nominal_length_units xml_buffer, uro_ifc_boundary_surface_attribute{}.uro_ifc_wall_standard_case_uro_nominal_width xml_real64, uro_ifc_boundary_surface_attribute{}.uro_ifc_wall_standard_case_uro_nominal_width_units xml_buffer, uro_ifc_boundary_surface_attribute{}.uro_ifc_wall_standard_case_uro_nominal_height xml_real64, uro_ifc_boundary_surface_attribute{}.uro_ifc_wall_standard_case_uro_nominal_height_units xml_buffer, uro_ifc_boundary_surface_attribute{}.uro_ifc_wall_standard_case_uro_gross_foot_print_area xml_real64, uro_ifc_boundary_surface_attribute{}.uro_ifc_wall_standard_case_uro_gross_foot_print_area_units xml_buffer,
      uro_ifc_boundary_surface_attribute{}.uro_ifc_wall_standard_case_uro_net_foot_print_area xml_real64, uro_ifc_boundary_surface_attribute{}.uro_ifc_wall_standard_case_uro_net_foot_print_area_units xml_buffer, uro_ifc_boundary_surface_attribute{}.uro_ifc_wall_standard_case_uro_gross_side_area xml_real64, uro_ifc_boundary_surface_attribute{}.uro_ifc_wall_standard_case_uro_gross_side_area_units xml_buffer, uro_ifc_boundary_surface_attribute{}.uro_ifc_wall_standard_case_uro_net_side_area xml_real64, uro_ifc_boundary_surface_attribute{}.uro_ifc_wall_standard_case_uro_net_side_area_units xml_buffer, uro_ifc_boundary_surface_attribute{}.uro_ifc_wall_standard_case_uro_gross_side_area_left xml_real64, uro_ifc_boundary_surface_attribute{}.uro_ifc_wall_standard_case_uro_gross_side_area_left_units xml_buffer, uro_ifc_boundary_surface_attribute{}.uro_ifc_wall_standard_case_uro_net_side_area_left xml_real64, uro_ifc_boundary_surface_attribute{}.uro_ifc_wall_standard_case_uro_net_side_area_left_units xml_buffer, uro_ifc_boundary_surface_attribute{}.uro_ifc_wall_standard_case_uro_gross_side_area_right xml_real64, uro_ifc_boundary_surface_attribute{}.uro_ifc_wall_standard_case_uro_gross_side_area_right_units xml_buffer, uro_ifc_boundary_surface_attribute{}.uro_ifc_wall_standard_case_uro_net_side_area_right xml_real64, uro_ifc_boundary_surface_attribute{}.uro_ifc_wall_standard_case_uro_net_side_area_right_units xml_buffer, uro_ifc_boundary_surface_attribute{}.uro_ifc_wall_standard_case_uro_gross_volume xml_real64, uro_ifc_boundary_surface_attribute{}.uro_ifc_wall_standard_case_uro_gross_volume_units xml_buffer, uro_ifc_boundary_surface_attribute{}.uro_ifc_wall_standard_case_uro_net_volume xml_real64, uro_ifc_boundary_surface_attribute{}.uro_ifc_wall_standard_case_uro_net_volume_units xml_buffer, uro_ifc_boundary_surface_attribute{}.uro_ifc_window_uro_global_id xml_buffer, uro_ifc_boundary_surface_attribute{}.uro_ifc_window_uro_name xml_buffer, uro_ifc_boundary_surface_attribute{}.uro_ifc_window_uro_description xml_buffer, uro_ifc_boundary_surface_attribute{}.uro_ifc_window_uro_object_type xml_buffer, uro_ifc_boundary_surface_attribute{}.uro_ifc_window_uro_tag xml_buffer, uro_ifc_boundary_surface_attribute{}.uro_ifc_window_uro_element_type xml_buffer, uro_ifc_boundary_surface_attribute{}.uro_ifc_window_uro_element_type_codeSpace xml_buffer, uro_ifc_boundary_surface_attribute{}.uro_ifc_window_uro_predefined_type xml_buffer, uro_ifc_boundary_surface_attribute{}.uro_ifc_window_uro_predefined_type_codeSpace xml_buffer, uro_ifc_boundary_surface_attribute{}.uro_ifc_window_uro_shape_type xml_buffer, uro_ifc_boundary_surface_attribute{}.uro_ifc_window_uro_shape_type_codeSpace xml_buffer, uro_ifc_boundary_surface_attribute{}.uro_ifc_window_uro_number_of_riser xml_int64,
      uro_ifc_boundary_surface_attribute{}.uro_ifc_window_uro_number_of_treads xml_int64, uro_ifc_boundary_surface_attribute{}.uro_ifc_window_uro_riser_height xml_int64, uro_ifc_boundary_surface_attribute{}.uro_ifc_window_uro_tread_length xml_int64, uro_ifc_boundary_surface_attribute{}.uro_ifc_window_uro_operation_type xml_char(11), uro_ifc_boundary_surface_attribute{}.uro_ifc_window_uro_capacity_by_weight xml_real64, uro_ifc_boundary_surface_attribute{}.uro_ifc_window_uro_capacity_by_weight_units xml_buffer, uro_ifc_boundary_surface_attribute{}.uro_ifc_window_uro_capacity_by_number xml_int64, uro_ifc_boundary_surface_attribute{}.uro_ifc_window_uro_overall_height xml_real64, uro_ifc_boundary_surface_attribute{}.uro_ifc_window_uro_overall_height_units xml_buffer, uro_ifc_boundary_surface_attribute{}.uro_ifc_window_uro_overall_width xml_real64, uro_ifc_boundary_surface_attribute{}.uro_ifc_window_uro_overall_width_units xml_buffer
OuterFloorSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, uro_ifc_boundary_surface_attribute{}.uro_ifc_building_uro_global_id xml_buffer, uro_ifc_boundary_surface_attribute{}.uro_ifc_building_uro_name xml_buffer, uro_ifc_boundary_surface_attribute{}.uro_ifc_building_uro_description xml_buffer, uro_ifc_boundary_surface_attribute{}.uro_ifc_building_uro_object_type xml_buffer, uro_ifc_boundary_surface_attribute{}.uro_ifc_building_uro_long_name xml_buffer, uro_ifc_boundary_surface_attribute{}.uro_ifc_building_uro_composition_type xml_char(7), uro_ifc_boundary_surface_attribute{}.uro_ifc_building_uro_elevation_of_ref_height xml_real64, uro_ifc_boundary_surface_attribute{}.uro_ifc_building_uro_elevation_of_ref_height_units xml_buffer, uro_ifc_boundary_surface_attribute{}.uro_ifc_building_uro_elevation_of_terrain xml_real64, uro_ifc_boundary_surface_attribute{}.uro_ifc_building_uro_elevation_of_terrain_units xml_buffer, uro_ifc_boundary_surface_attribute{}.uro_ifc_building_uro_building_address_xlink_href xml_buffer, uro_ifc_boundary_surface_attribute{}.uro_ifc_building_element_uro_global_id xml_buffer, uro_ifc_boundary_surface_attribute{}.uro_ifc_building_element_uro_name xml_buffer, uro_ifc_boundary_surface_attribute{}.uro_ifc_building_element_uro_description xml_buffer,
      uro_ifc_boundary_surface_attribute{}.uro_ifc_building_element_uro_object_type xml_buffer, uro_ifc_boundary_surface_attribute{}.uro_ifc_building_element_uro_tag xml_buffer, uro_ifc_boundary_surface_attribute{}.uro_ifc_building_element_uro_element_type xml_buffer, uro_ifc_boundary_surface_attribute{}.uro_ifc_building_element_uro_element_type_codeSpace xml_buffer, uro_ifc_boundary_surface_attribute{}.uro_ifc_building_element_uro_predefined_type xml_buffer, uro_ifc_boundary_surface_attribute{}.uro_ifc_building_element_uro_predefined_type_codeSpace xml_buffer, uro_ifc_boundary_surface_attribute{}.uro_ifc_building_element_uro_shape_type xml_buffer, uro_ifc_boundary_surface_attribute{}.uro_ifc_building_element_uro_shape_type_codeSpace xml_buffer, uro_ifc_boundary_surface_attribute{}.uro_ifc_building_element_uro_number_of_riser xml_int64, uro_ifc_boundary_surface_attribute{}.uro_ifc_building_element_uro_number_of_treads xml_int64, uro_ifc_boundary_surface_attribute{}.uro_ifc_building_element_uro_riser_height xml_int64, uro_ifc_boundary_surface_attribute{}.uro_ifc_building_element_uro_tread_length xml_int64, uro_ifc_boundary_surface_attribute{}.uro_ifc_building_element_uro_operation_type xml_char(11), uro_ifc_boundary_surface_attribute{}.uro_ifc_building_element_uro_capacity_by_weight xml_real64, uro_ifc_boundary_surface_attribute{}.uro_ifc_building_element_uro_capacity_by_weight_units xml_buffer, uro_ifc_boundary_surface_attribute{}.uro_ifc_building_element_uro_capacity_by_number xml_int64, uro_ifc_boundary_surface_attribute{}.uro_ifc_building_storey_uro_global_id xml_buffer, uro_ifc_boundary_surface_attribute{}.uro_ifc_building_storey_uro_name xml_buffer, uro_ifc_boundary_surface_attribute{}.uro_ifc_building_storey_uro_description xml_buffer, uro_ifc_boundary_surface_attribute{}.uro_ifc_building_storey_uro_object_type xml_buffer, uro_ifc_boundary_surface_attribute{}.uro_ifc_building_storey_uro_long_name xml_buffer, uro_ifc_boundary_surface_attribute{}.uro_ifc_building_storey_uro_composition_type xml_char(7), uro_ifc_boundary_surface_attribute{}.uro_ifc_building_storey_uro_elevation xml_real64, uro_ifc_boundary_surface_attribute{}.uro_ifc_building_storey_uro_elevation_units xml_buffer, uro_ifc_boundary_surface_attribute{}.uro_ifc_classification_reference_uro_location xml_buffer, uro_ifc_boundary_surface_attribute{}.uro_ifc_classification_reference_uro_item_reference xml_buffer, uro_ifc_boundary_surface_attribute{}.uro_ifc_classification_reference_uro_item_reference_codeSpace xml_buffer, uro_ifc_boundary_surface_attribute{}.uro_ifc_classification_reference_uro_name xml_buffer, uro_ifc_boundary_surface_attribute{}.uro_ifc_classification_reference_uro_name_codeSpace xml_buffer, uro_ifc_boundary_surface_attribute{}.uro_ifc_classification_reference_uro_reference_source_uro_ifc_classification_uro_source xml_buffer,
      uro_ifc_boundary_surface_attribute{}.uro_ifc_classification_reference_uro_reference_source_uro_ifc_classification_uro_edition xml_buffer, uro_ifc_boundary_surface_attribute{}.uro_ifc_classification_reference_uro_reference_source_uro_ifc_classification_uro_edition_date xml_date, uro_ifc_boundary_surface_attribute{}.uro_ifc_classification_reference_uro_reference_source_uro_ifc_classification_uro_name xml_buffer, uro_ifc_boundary_surface_attribute{}.uro_ifc_coordinate_reference_system_uro_name xml_buffer, uro_ifc_boundary_surface_attribute{}.uro_ifc_coordinate_reference_system_uro_description xml_buffer, uro_ifc_boundary_surface_attribute{}.uro_ifc_coordinate_reference_system_uro_geodetic_datum xml_buffer, uro_ifc_boundary_surface_attribute{}.uro_ifc_coordinate_reference_system_uro_vertical_datum xml_buffer, uro_ifc_boundary_surface_attribute{}.uro_ifc_curtain_wall_uro_global_id xml_buffer, uro_ifc_boundary_surface_attribute{}.uro_ifc_curtain_wall_uro_name xml_buffer, uro_ifc_boundary_surface_attribute{}.uro_ifc_curtain_wall_uro_description xml_buffer, uro_ifc_boundary_surface_attribute{}.uro_ifc_curtain_wall_uro_object_type xml_buffer, uro_ifc_boundary_surface_attribute{}.uro_ifc_curtain_wall_uro_tag xml_buffer, uro_ifc_boundary_surface_attribute{}.uro_ifc_curtain_wall_uro_element_type xml_buffer, uro_ifc_boundary_surface_attribute{}.uro_ifc_curtain_wall_uro_element_type_codeSpace xml_buffer, uro_ifc_boundary_surface_attribute{}.uro_ifc_curtain_wall_uro_predefined_type xml_buffer, uro_ifc_boundary_surface_attribute{}.uro_ifc_curtain_wall_uro_predefined_type_codeSpace xml_buffer, uro_ifc_boundary_surface_attribute{}.uro_ifc_curtain_wall_uro_shape_type xml_buffer, uro_ifc_boundary_surface_attribute{}.uro_ifc_curtain_wall_uro_shape_type_codeSpace xml_buffer, uro_ifc_boundary_surface_attribute{}.uro_ifc_curtain_wall_uro_number_of_riser xml_int64, uro_ifc_boundary_surface_attribute{}.uro_ifc_curtain_wall_uro_number_of_treads xml_int64, uro_ifc_boundary_surface_attribute{}.uro_ifc_curtain_wall_uro_riser_height xml_int64, uro_ifc_boundary_surface_attribute{}.uro_ifc_curtain_wall_uro_tread_length xml_int64, uro_ifc_boundary_surface_attribute{}.uro_ifc_curtain_wall_uro_operation_type xml_char(11), uro_ifc_boundary_surface_attribute{}.uro_ifc_curtain_wall_uro_capacity_by_weight xml_real64, uro_ifc_boundary_surface_attribute{}.uro_ifc_curtain_wall_uro_capacity_by_weight_units xml_buffer, uro_ifc_boundary_surface_attribute{}.uro_ifc_curtain_wall_uro_capacity_by_number xml_int64, uro_ifc_boundary_surface_attribute{}.uro_ifc_door_uro_global_id xml_buffer, uro_ifc_boundary_surface_attribute{}.uro_ifc_door_uro_name xml_buffer, uro_ifc_boundary_surface_attribute{}.uro_ifc_door_uro_description xml_buffer, uro_ifc_boundary_surface_attribute{}.uro_ifc_door_uro_object_type xml_buffer,
      uro_ifc_boundary_surface_attribute{}.uro_ifc_door_uro_tag xml_buffer, uro_ifc_boundary_surface_attribute{}.uro_ifc_door_uro_element_type xml_buffer, uro_ifc_boundary_surface_attribute{}.uro_ifc_door_uro_element_type_codeSpace xml_buffer, uro_ifc_boundary_surface_attribute{}.uro_ifc_door_uro_predefined_type xml_buffer, uro_ifc_boundary_surface_attribute{}.uro_ifc_door_uro_predefined_type_codeSpace xml_buffer, uro_ifc_boundary_surface_attribute{}.uro_ifc_door_uro_shape_type xml_buffer, uro_ifc_boundary_surface_attribute{}.uro_ifc_door_uro_shape_type_codeSpace xml_buffer, uro_ifc_boundary_surface_attribute{}.uro_ifc_door_uro_number_of_riser xml_int64, uro_ifc_boundary_surface_attribute{}.uro_ifc_door_uro_number_of_treads xml_int64, uro_ifc_boundary_surface_attribute{}.uro_ifc_door_uro_riser_height xml_int64, uro_ifc_boundary_surface_attribute{}.uro_ifc_door_uro_tread_length xml_int64, uro_ifc_boundary_surface_attribute{}.uro_ifc_door_uro_operation_type xml_char(11), uro_ifc_boundary_surface_attribute{}.uro_ifc_door_uro_capacity_by_weight xml_real64, uro_ifc_boundary_surface_attribute{}.uro_ifc_door_uro_capacity_by_weight_units xml_buffer, uro_ifc_boundary_surface_attribute{}.uro_ifc_door_uro_capacity_by_number xml_int64, uro_ifc_boundary_surface_attribute{}.uro_ifc_door_uro_overall_height xml_real64, uro_ifc_boundary_surface_attribute{}.uro_ifc_door_uro_overall_height_units xml_buffer, uro_ifc_boundary_surface_attribute{}.uro_ifc_door_uro_overall_width xml_real64, uro_ifc_boundary_surface_attribute{}.uro_ifc_door_uro_overall_width_units xml_buffer, uro_ifc_boundary_surface_attribute{}.uro_ifc_furnishing_element_uro_global_id xml_buffer, uro_ifc_boundary_surface_attribute{}.uro_ifc_furnishing_element_uro_name xml_buffer, uro_ifc_boundary_surface_attribute{}.uro_ifc_furnishing_element_uro_description xml_buffer, uro_ifc_boundary_surface_attribute{}.uro_ifc_furnishing_element_uro_object_type xml_buffer, uro_ifc_boundary_surface_attribute{}.uro_ifc_furnishing_element_uro_tag xml_buffer, uro_ifc_boundary_surface_attribute{}.uro_ifc_map_conversion_uro_source_crs_uro_crs_uro_ifc_projected_crs_uro_name xml_buffer, uro_ifc_boundary_surface_attribute{}.uro_ifc_map_conversion_uro_source_crs_uro_crs_uro_ifc_projected_crs_uro_description xml_buffer, uro_ifc_boundary_surface_attribute{}.uro_ifc_map_conversion_uro_source_crs_uro_crs_uro_ifc_projected_crs_uro_geodetic_datum xml_buffer, uro_ifc_boundary_surface_attribute{}.uro_ifc_map_conversion_uro_source_crs_uro_crs_uro_ifc_projected_crs_uro_vertical_datum xml_buffer, uro_ifc_boundary_surface_attribute{}.uro_ifc_map_conversion_uro_source_crs_uro_crs_uro_ifc_projected_crs_uro_map_unit xml_buffer, uro_ifc_boundary_surface_attribute{}.uro_ifc_map_conversion_uro_source_crs_uro_crs_uro_ifc_projected_crs_uro_map_projection xml_buffer,
      uro_ifc_boundary_surface_attribute{}.uro_ifc_map_conversion_uro_source_crs_uro_crs_uro_ifc_projected_crs_uro_map_zone xml_buffer, uro_ifc_boundary_surface_attribute{}.uro_ifc_map_conversion_uro_source_crs_uro_crs_uro_ifc_coordinate_reference_system_uro_name xml_buffer, uro_ifc_boundary_surface_attribute{}.uro_ifc_map_conversion_uro_source_crs_uro_crs_uro_ifc_coordinate_reference_system_uro_description xml_buffer, uro_ifc_boundary_surface_attribute{}.uro_ifc_map_conversion_uro_source_crs_uro_crs_uro_ifc_coordinate_reference_system_uro_geodetic_datum xml_buffer, uro_ifc_boundary_surface_attribute{}.uro_ifc_map_conversion_uro_source_crs_uro_crs_uro_ifc_coordinate_reference_system_uro_vertical_datum xml_buffer, uro_ifc_boundary_surface_attribute{}.uro_ifc_map_conversion_uro_source_crs_uro_context_uro_ifc_geometric_representation_context_uro_context_identifier xml_buffer, uro_ifc_boundary_surface_attribute{}.uro_ifc_map_conversion_uro_source_crs_uro_context_uro_ifc_geometric_representation_context_uro_context_type xml_buffer, uro_ifc_boundary_surface_attribute{}.uro_ifc_map_conversion_uro_source_crs_uro_context_uro_ifc_geometric_representation_context_uro_coordinate_space_dimension xml_int64, uro_ifc_boundary_surface_attribute{}.uro_ifc_map_conversion_uro_source_crs_uro_context_uro_ifc_geometric_representation_context_uro_precision xml_real64, uro_ifc_boundary_surface_attribute{}.uro_ifc_map_conversion_uro_source_crs_uro_context_uro_ifc_geometric_representation_context_uro_true_north xml_real64, uro_ifc_boundary_surface_attribute{}.uro_ifc_map_conversion_uro_target_crs_uro_ifc_projected_crs_uro_name xml_buffer, uro_ifc_boundary_surface_attribute{}.uro_ifc_map_conversion_uro_target_crs_uro_ifc_projected_crs_uro_description xml_buffer, uro_ifc_boundary_surface_attribute{}.uro_ifc_map_conversion_uro_target_crs_uro_ifc_projected_crs_uro_geodetic_datum xml_buffer, uro_ifc_boundary_surface_attribute{}.uro_ifc_map_conversion_uro_target_crs_uro_ifc_projected_crs_uro_vertical_datum xml_buffer, uro_ifc_boundary_surface_attribute{}.uro_ifc_map_conversion_uro_target_crs_uro_ifc_projected_crs_uro_map_unit xml_buffer, uro_ifc_boundary_surface_attribute{}.uro_ifc_map_conversion_uro_target_crs_uro_ifc_projected_crs_uro_map_projection xml_buffer, uro_ifc_boundary_surface_attribute{}.uro_ifc_map_conversion_uro_target_crs_uro_ifc_projected_crs_uro_map_zone xml_buffer, uro_ifc_boundary_surface_attribute{}.uro_ifc_map_conversion_uro_target_crs_uro_ifc_coordinate_reference_system_uro_name xml_buffer, uro_ifc_boundary_surface_attribute{}.uro_ifc_map_conversion_uro_target_crs_uro_ifc_coordinate_reference_system_uro_description xml_buffer, uro_ifc_boundary_surface_attribute{}.uro_ifc_map_conversion_uro_target_crs_uro_ifc_coordinate_reference_system_uro_geodetic_datum xml_buffer, uro_ifc_boundary_surface_attribute{}.uro_ifc_map_conversion_uro_target_crs_uro_ifc_coordinate_reference_system_uro_vertical_datum xml_buffer, uro_ifc_boundary_surface_attribute{}.uro_ifc_map_conversion_uro_eastings xml_buffer, uro_ifc_boundary_surface_attribute{}.uro_ifc_map_conversion_uro_northings xml_buffer, uro_ifc_boundary_surface_attribute{}.uro_ifc_map_conversion_uro_orthogonal_height xml_real64, uro_ifc_boundary_surface_attribute{}.uro_ifc_map_conversion_uro_orthogonal_height_units xml_buffer, uro_ifc_boundary_surface_attribute{}.uro_ifc_map_conversion_uro_x_axis_abscissa xml_real64, uro_ifc_boundary_surface_attribute{}.uro_ifc_map_conversion_uro_x_axis_ordinate xml_real64, uro_ifc_boundary_surface_attribute{}.uro_ifc_map_conversion_uro_scale xml_real64, uro_ifc_boundary_surface_attribute{}.uro_ifc_opening_element_uro_global_id xml_buffer, uro_ifc_boundary_surface_attribute{}.uro_ifc_opening_element_uro_name xml_buffer,
      uro_ifc_boundary_surface_attribute{}.uro_ifc_opening_element_uro_description xml_buffer, uro_ifc_boundary_surface_attribute{}.uro_ifc_opening_element_uro_object_type xml_buffer, uro_ifc_boundary_surface_attribute{}.uro_ifc_opening_element_uro_tag xml_buffer, uro_ifc_boundary_surface_attribute{}.uro_ifc_opening_element_uro_nominal_area xml_real64, uro_ifc_boundary_surface_attribute{}.uro_ifc_opening_element_uro_nominal_area_units xml_buffer, uro_ifc_boundary_surface_attribute{}.uro_ifc_opening_element_uro_nominal_volume xml_real64, uro_ifc_boundary_surface_attribute{}.uro_ifc_opening_element_uro_nominal_volume_units xml_buffer, uro_ifc_boundary_surface_attribute{}.uro_ifc_project_uro_global_id xml_buffer, uro_ifc_boundary_surface_attribute{}.uro_ifc_project_uro_name xml_buffer, uro_ifc_boundary_surface_attribute{}.uro_ifc_project_uro_description xml_buffer, uro_ifc_boundary_surface_attribute{}.uro_ifc_project_uro_object_type xml_buffer, uro_ifc_boundary_surface_attribute{}.uro_ifc_project_uro_long_name xml_buffer, uro_ifc_boundary_surface_attribute{}.uro_ifc_project_uro_phase xml_buffer, uro_ifc_boundary_surface_attribute{}.uro_ifc_project_uro_representation_contexts_uro_ifc_geometric_representation_context_uro_context_identifier xml_buffer, uro_ifc_boundary_surface_attribute{}.uro_ifc_project_uro_representation_contexts_uro_ifc_geometric_representation_context_uro_context_type xml_buffer, uro_ifc_boundary_surface_attribute{}.uro_ifc_project_uro_representation_contexts_uro_ifc_geometric_representation_context_uro_coordinate_space_dimension xml_int64, uro_ifc_boundary_surface_attribute{}.uro_ifc_project_uro_representation_contexts_uro_ifc_geometric_representation_context_uro_precision xml_real64, uro_ifc_boundary_surface_attribute{}.uro_ifc_project_uro_representation_contexts_uro_ifc_geometric_representation_context_uro_true_north xml_real64, uro_ifc_boundary_surface_attribute{}.uro_ifc_project_uro_units_in_context{}.uro_ifc_unit_uro_dimensions xml_int64, uro_ifc_boundary_surface_attribute{}.uro_ifc_project_uro_units_in_context{}.uro_ifc_unit_uro_unit_type xml_char(28), uro_ifc_boundary_surface_attribute{}.uro_ifc_project_uro_units_in_context{}.uro_ifc_unit_uro_perfix xml_buffer, uro_ifc_boundary_surface_attribute{}.uro_ifc_project_uro_units_in_context{}.uro_ifc_unit_uro_name xml_buffer, uro_ifc_boundary_surface_attribute{}.uro_ifc_projected_crs_uro_name xml_buffer, uro_ifc_boundary_surface_attribute{}.uro_ifc_projected_crs_uro_description xml_buffer, uro_ifc_boundary_surface_attribute{}.uro_ifc_projected_crs_uro_geodetic_datum xml_buffer, uro_ifc_boundary_surface_attribute{}.uro_ifc_projected_crs_uro_vertical_datum xml_buffer, uro_ifc_boundary_surface_attribute{}.uro_ifc_projected_crs_uro_map_unit xml_buffer, uro_ifc_boundary_surface_attribute{}.uro_ifc_projected_crs_uro_map_projection xml_buffer, uro_ifc_boundary_surface_attribute{}.uro_ifc_projected_crs_uro_map_zone xml_buffer, uro_ifc_boundary_surface_attribute{}.uro_ifc_pset_building_common_uro_building_id xml_real64,
      uro_ifc_boundary_surface_attribute{}.uro_ifc_pset_building_common_uro_building_id_units xml_buffer, uro_ifc_boundary_surface_attribute{}.uro_ifc_pset_building_common_uro_is_permanent_id xml_real64, uro_ifc_boundary_surface_attribute{}.uro_ifc_pset_building_common_uro_is_permanent_id_units xml_buffer, uro_ifc_boundary_surface_attribute{}.uro_ifc_pset_building_common_uro_main_fire_use xml_buffer, uro_ifc_boundary_surface_attribute{}.uro_ifc_pset_building_common_uro_ancillary_fire_use xml_buffer, uro_ifc_boundary_surface_attribute{}.uro_ifc_pset_building_common_uro_sprinkler_protection xml_boolean, uro_ifc_boundary_surface_attribute{}.uro_ifc_pset_building_common_uro_sprinkler_protection_automatic xml_boolean, uro_ifc_boundary_surface_attribute{}.uro_ifc_pset_building_common_uro_occupancy_type xml_buffer, uro_ifc_boundary_surface_attribute{}.uro_ifc_pset_building_common_uro_occupancy_type_codeSpace xml_buffer, uro_ifc_boundary_surface_attribute{}.uro_ifc_pset_building_common_uro_gross_planned_area xml_real64, uro_ifc_boundary_surface_attribute{}.uro_ifc_pset_building_common_uro_gross_planned_area_units xml_buffer, uro_ifc_boundary_surface_attribute{}.uro_ifc_pset_building_common_uro_number_of_storeys xml_int64, uro_ifc_boundary_surface_attribute{}.uro_ifc_pset_building_common_uro_year_of_construction xml_buffer, uro_ifc_boundary_surface_attribute{}.uro_ifc_pset_building_common_uro_is_landmarked xml_boolean, uro_ifc_boundary_surface_attribute{}.uro_ifc_pset_door_common_uro_reference xml_buffer, uro_ifc_boundary_surface_attribute{}.uro_ifc_pset_door_common_uro_acoustic_rating xml_buffer, uro_ifc_boundary_surface_attribute{}.uro_ifc_pset_door_common_uro_firerating xml_buffer, uro_ifc_boundary_surface_attribute{}.uro_ifc_pset_door_common_uro_security_rating xml_buffer, uro_ifc_boundary_surface_attribute{}.uro_ifc_pset_door_common_uro_is_external xml_boolean, uro_ifc_boundary_surface_attribute{}.uro_ifc_pset_door_common_uro_infiltration xml_real64, uro_ifc_boundary_surface_attribute{}.uro_ifc_pset_door_common_uro_thermal_transmittance xml_real64, uro_ifc_boundary_surface_attribute{}.uro_ifc_pset_door_common_uro_glazing_area_fraction xml_real64, uro_ifc_boundary_surface_attribute{}.uro_ifc_pset_door_common_uro_handicap_accessible xml_real64, uro_ifc_boundary_surface_attribute{}.uro_ifc_pset_door_common_uro_fire_exit xml_boolean, uro_ifc_boundary_surface_attribute{}.uro_ifc_pset_door_common_uro_self_closing xml_real64, uro_ifc_boundary_surface_attribute{}.uro_ifc_pset_door_common_uro_smoke_stop xml_boolean, uro_ifc_boundary_surface_attribute{}.uro_ifc_pset_opening_element_common_uro_reference xml_buffer, uro_ifc_boundary_surface_attribute{}.uro_ifc_pset_opening_element_common_uro_purpose xml_buffer, uro_ifc_boundary_surface_attribute{}.uro_ifc_pset_opening_element_common_uro_fire_exit xml_boolean, uro_ifc_boundary_surface_attribute{}.uro_ifc_pset_opening_element_common_uro_protected_opening xml_boolean,
      uro_ifc_boundary_surface_attribute{}.uro_ifc_pset_opening_element_common_uro_parallel_jambs xml_boolean, uro_ifc_boundary_surface_attribute{}.uro_ifc_pset_site_common_uro_buildable_area xml_real64, uro_ifc_boundary_surface_attribute{}.uro_ifc_pset_site_common_uro_buildable_area_units xml_buffer, uro_ifc_boundary_surface_attribute{}.uro_ifc_pset_site_common_uro_total_area xml_real64, uro_ifc_boundary_surface_attribute{}.uro_ifc_pset_site_common_uro_total_area_units xml_buffer, uro_ifc_boundary_surface_attribute{}.uro_ifc_pset_site_common_uro_building_height_limit xml_real64, uro_ifc_boundary_surface_attribute{}.uro_ifc_pset_site_common_uro_building_height_limit_units xml_buffer, uro_ifc_boundary_surface_attribute{}.uro_ifc_pset_space_common_uro_reference xml_buffer, uro_ifc_boundary_surface_attribute{}.uro_ifc_pset_space_common_uro_category xml_buffer, uro_ifc_boundary_surface_attribute{}.uro_ifc_pset_space_common_uro_category_codeSpace xml_buffer, uro_ifc_boundary_surface_attribute{}.uro_ifc_pset_space_common_uro_floor_covering xml_buffer, uro_ifc_boundary_surface_attribute{}.uro_ifc_pset_space_common_uro_wall_covering xml_buffer, uro_ifc_boundary_surface_attribute{}.uro_ifc_pset_space_common_uro_ceiling_covering xml_buffer, uro_ifc_boundary_surface_attribute{}.uro_ifc_pset_space_common_uro_skirting_covering xml_buffer, uro_ifc_boundary_surface_attribute{}.uro_ifc_pset_space_common_uro_gross_planned_area xml_real64, uro_ifc_boundary_surface_attribute{}.uro_ifc_pset_space_common_uro_gross_planned_area_units xml_buffer, uro_ifc_boundary_surface_attribute{}.uro_ifc_pset_space_common_uro_net_planned_area xml_real64, uro_ifc_boundary_surface_attribute{}.uro_ifc_pset_space_common_uro_net_planned_area_units xml_buffer, uro_ifc_boundary_surface_attribute{}.uro_ifc_pset_space_common_uro_publicly_accessible xml_boolean, uro_ifc_boundary_surface_attribute{}.uro_ifc_pset_space_common_uro_handicap_accessible xml_boolean, uro_ifc_boundary_surface_attribute{}.uro_ifc_pset_space_common_uro_concealed_flooring xml_boolean, uro_ifc_boundary_surface_attribute{}.uro_ifc_pset_space_common_uro_concealed_ceiling xml_boolean, uro_ifc_boundary_surface_attribute{}.uro_ifc_pset_window_common_uro_reference xml_buffer, uro_ifc_boundary_surface_attribute{}.uro_ifc_pset_window_common_uro_acoustic_rating xml_buffer, uro_ifc_boundary_surface_attribute{}.uro_ifc_pset_window_common_uro_firerating xml_buffer, uro_ifc_boundary_surface_attribute{}.uro_ifc_pset_window_common_uro_security_rating xml_buffer, uro_ifc_boundary_surface_attribute{}.uro_ifc_pset_window_common_uro_is_external xml_boolean, uro_ifc_boundary_surface_attribute{}.uro_ifc_pset_window_common_uro_infiltration xml_real64, uro_ifc_boundary_surface_attribute{}.uro_ifc_pset_window_common_uro_thermal_transmittance xml_real64, uro_ifc_boundary_surface_attribute{}.uro_ifc_pset_window_common_uro_glazing_area_fraction xml_real64,
      uro_ifc_boundary_surface_attribute{}.uro_ifc_pset_window_common_uro_smoke_stop xml_boolean, uro_ifc_boundary_surface_attribute{}.uro_ifc_site_uro_global_id xml_buffer, uro_ifc_boundary_surface_attribute{}.uro_ifc_site_uro_name xml_buffer, uro_ifc_boundary_surface_attribute{}.uro_ifc_site_uro_description xml_buffer, uro_ifc_boundary_surface_attribute{}.uro_ifc_site_uro_object_type xml_buffer, uro_ifc_boundary_surface_attribute{}.uro_ifc_site_uro_long_name xml_buffer, uro_ifc_boundary_surface_attribute{}.uro_ifc_site_uro_composition_type xml_char(7), uro_ifc_boundary_surface_attribute{}.uro_ifc_site_uro_ref_longitude xml_real64, uro_ifc_boundary_surface_attribute{}.uro_ifc_site_uro_ref_latitude xml_real64, uro_ifc_boundary_surface_attribute{}.uro_ifc_site_uro_ref_elevation xml_real64, uro_ifc_boundary_surface_attribute{}.uro_ifc_site_uro_ref_elevation_units xml_buffer, uro_ifc_boundary_surface_attribute{}.uro_ifc_site_uro_land_title_number xml_buffer, uro_ifc_boundary_surface_attribute{}.uro_ifc_site_uro_site_address_xlink_href xml_buffer, uro_ifc_boundary_surface_attribute{}.uro_ifc_space_uro_global_id xml_buffer, uro_ifc_boundary_surface_attribute{}.uro_ifc_space_uro_name xml_buffer, uro_ifc_boundary_surface_attribute{}.uro_ifc_space_uro_description xml_buffer, uro_ifc_boundary_surface_attribute{}.uro_ifc_space_uro_object_type xml_buffer, uro_ifc_boundary_surface_attribute{}.uro_ifc_space_uro_long_name xml_buffer, uro_ifc_boundary_surface_attribute{}.uro_ifc_space_uro_composition_type xml_char(7), uro_ifc_boundary_surface_attribute{}.uro_ifc_space_uro_interioror_exterior_space xml_char(10), uro_ifc_boundary_surface_attribute{}.uro_ifc_space_uro_elevation_with_flooring xml_real64, uro_ifc_boundary_surface_attribute{}.uro_ifc_space_uro_elevation_with_flooring_units xml_buffer, uro_ifc_boundary_surface_attribute{}.uro_ifc_space_base_quantity_uro_nominal_height xml_real64, uro_ifc_boundary_surface_attribute{}.uro_ifc_space_base_quantity_uro_nominal_height_units xml_buffer, uro_ifc_boundary_surface_attribute{}.uro_ifc_space_base_quantity_uro_clear_height xml_real64, uro_ifc_boundary_surface_attribute{}.uro_ifc_space_base_quantity_uro_clear_height_units xml_buffer, uro_ifc_boundary_surface_attribute{}.uro_ifc_space_base_quantity_uro_finish_ceiling_height xml_real64, uro_ifc_boundary_surface_attribute{}.uro_ifc_space_base_quantity_uro_finish_ceiling_height_units xml_buffer, uro_ifc_boundary_surface_attribute{}.uro_ifc_space_base_quantity_uro_gross_perimeter xml_real64, uro_ifc_boundary_surface_attribute{}.uro_ifc_space_base_quantity_uro_gross_perimeter_units xml_buffer,
      uro_ifc_boundary_surface_attribute{}.uro_ifc_space_base_quantity_uro_net_perimeter xml_real64, uro_ifc_boundary_surface_attribute{}.uro_ifc_space_base_quantity_uro_net_perimeter_units xml_buffer, uro_ifc_boundary_surface_attribute{}.uro_ifc_space_base_quantity_uro_gross_ceiling_area xml_real64, uro_ifc_boundary_surface_attribute{}.uro_ifc_space_base_quantity_uro_gross_ceiling_area_units xml_buffer, uro_ifc_boundary_surface_attribute{}.uro_ifc_space_base_quantity_uro_gross_floor_area xml_real64, uro_ifc_boundary_surface_attribute{}.uro_ifc_space_base_quantity_uro_gross_floor_area_units xml_buffer, uro_ifc_boundary_surface_attribute{}.uro_ifc_space_base_quantity_uro_net_ceiling_area xml_real64, uro_ifc_boundary_surface_attribute{}.uro_ifc_space_base_quantity_uro_net_ceiling_area_units xml_buffer, uro_ifc_boundary_surface_attribute{}.uro_ifc_space_base_quantity_uro_net_floor_area xml_real64, uro_ifc_boundary_surface_attribute{}.uro_ifc_space_base_quantity_uro_net_floor_area_units xml_buffer, uro_ifc_boundary_surface_attribute{}.uro_ifc_space_base_quantity_uro_gross_wall_area xml_real64, uro_ifc_boundary_surface_attribute{}.uro_ifc_space_base_quantity_uro_gross_wall_area_units xml_buffer, uro_ifc_boundary_surface_attribute{}.uro_ifc_space_base_quantity_uro_net_wall_area xml_real64, uro_ifc_boundary_surface_attribute{}.uro_ifc_space_base_quantity_uro_net_wall_area_units xml_buffer, uro_ifc_boundary_surface_attribute{}.uro_ifc_space_base_quantity_uro_gross_volume xml_real64, uro_ifc_boundary_surface_attribute{}.uro_ifc_space_base_quantity_uro_gross_volume_units xml_buffer, uro_ifc_boundary_surface_attribute{}.uro_ifc_space_base_quantity_uro_net_volume xml_real64, uro_ifc_boundary_surface_attribute{}.uro_ifc_space_base_quantity_uro_net_volume_units xml_buffer, uro_ifc_boundary_surface_attribute{}.uro_ifc_wall_uro_global_id xml_buffer, uro_ifc_boundary_surface_attribute{}.uro_ifc_wall_uro_name xml_buffer, uro_ifc_boundary_surface_attribute{}.uro_ifc_wall_uro_description xml_buffer, uro_ifc_boundary_surface_attribute{}.uro_ifc_wall_uro_object_type xml_buffer, uro_ifc_boundary_surface_attribute{}.uro_ifc_wall_uro_tag xml_buffer, uro_ifc_boundary_surface_attribute{}.uro_ifc_wall_uro_element_type xml_buffer, uro_ifc_boundary_surface_attribute{}.uro_ifc_wall_uro_element_type_codeSpace xml_buffer, uro_ifc_boundary_surface_attribute{}.uro_ifc_wall_uro_predefined_type xml_buffer, uro_ifc_boundary_surface_attribute{}.uro_ifc_wall_uro_predefined_type_codeSpace xml_buffer, uro_ifc_boundary_surface_attribute{}.uro_ifc_wall_uro_shape_type xml_buffer, uro_ifc_boundary_surface_attribute{}.uro_ifc_wall_uro_shape_type_codeSpace xml_buffer, uro_ifc_boundary_surface_attribute{}.uro_ifc_wall_uro_number_of_riser xml_int64,
      uro_ifc_boundary_surface_attribute{}.uro_ifc_wall_uro_number_of_treads xml_int64, uro_ifc_boundary_surface_attribute{}.uro_ifc_wall_uro_riser_height xml_int64, uro_ifc_boundary_surface_attribute{}.uro_ifc_wall_uro_tread_length xml_int64, uro_ifc_boundary_surface_attribute{}.uro_ifc_wall_uro_operation_type xml_char(11), uro_ifc_boundary_surface_attribute{}.uro_ifc_wall_uro_capacity_by_weight xml_real64, uro_ifc_boundary_surface_attribute{}.uro_ifc_wall_uro_capacity_by_weight_units xml_buffer, uro_ifc_boundary_surface_attribute{}.uro_ifc_wall_uro_capacity_by_number xml_int64, uro_ifc_boundary_surface_attribute{}.uro_ifc_wall_uro_nominal_length xml_real64, uro_ifc_boundary_surface_attribute{}.uro_ifc_wall_uro_nominal_length_units xml_buffer, uro_ifc_boundary_surface_attribute{}.uro_ifc_wall_uro_nominal_width xml_real64, uro_ifc_boundary_surface_attribute{}.uro_ifc_wall_uro_nominal_width_units xml_buffer, uro_ifc_boundary_surface_attribute{}.uro_ifc_wall_uro_nominal_height xml_real64, uro_ifc_boundary_surface_attribute{}.uro_ifc_wall_uro_nominal_height_units xml_buffer, uro_ifc_boundary_surface_attribute{}.uro_ifc_wall_uro_gross_foot_print_area xml_real64, uro_ifc_boundary_surface_attribute{}.uro_ifc_wall_uro_gross_foot_print_area_units xml_buffer, uro_ifc_boundary_surface_attribute{}.uro_ifc_wall_uro_net_foot_print_area xml_real64, uro_ifc_boundary_surface_attribute{}.uro_ifc_wall_uro_net_foot_print_area_units xml_buffer, uro_ifc_boundary_surface_attribute{}.uro_ifc_wall_uro_gross_side_area xml_real64, uro_ifc_boundary_surface_attribute{}.uro_ifc_wall_uro_gross_side_area_units xml_buffer, uro_ifc_boundary_surface_attribute{}.uro_ifc_wall_uro_net_side_area xml_real64, uro_ifc_boundary_surface_attribute{}.uro_ifc_wall_uro_net_side_area_units xml_buffer, uro_ifc_boundary_surface_attribute{}.uro_ifc_wall_uro_gross_side_area_left xml_real64, uro_ifc_boundary_surface_attribute{}.uro_ifc_wall_uro_gross_side_area_left_units xml_buffer, uro_ifc_boundary_surface_attribute{}.uro_ifc_wall_uro_net_side_area_left xml_real64, uro_ifc_boundary_surface_attribute{}.uro_ifc_wall_uro_net_side_area_left_units xml_buffer, uro_ifc_boundary_surface_attribute{}.uro_ifc_wall_uro_gross_side_area_right xml_real64, uro_ifc_boundary_surface_attribute{}.uro_ifc_wall_uro_gross_side_area_right_units xml_buffer, uro_ifc_boundary_surface_attribute{}.uro_ifc_wall_uro_net_side_area_right xml_real64, uro_ifc_boundary_surface_attribute{}.uro_ifc_wall_uro_net_side_area_right_units xml_buffer, uro_ifc_boundary_surface_attribute{}.uro_ifc_wall_uro_gross_volume xml_real64,
      uro_ifc_boundary_surface_attribute{}.uro_ifc_wall_uro_gross_volume_units xml_buffer, uro_ifc_boundary_surface_attribute{}.uro_ifc_wall_uro_net_volume xml_real64, uro_ifc_boundary_surface_attribute{}.uro_ifc_wall_uro_net_volume_units xml_buffer, uro_ifc_boundary_surface_attribute{}.uro_ifc_wall_standard_case_uro_global_id xml_buffer, uro_ifc_boundary_surface_attribute{}.uro_ifc_wall_standard_case_uro_name xml_buffer, uro_ifc_boundary_surface_attribute{}.uro_ifc_wall_standard_case_uro_description xml_buffer, uro_ifc_boundary_surface_attribute{}.uro_ifc_wall_standard_case_uro_object_type xml_buffer, uro_ifc_boundary_surface_attribute{}.uro_ifc_wall_standard_case_uro_tag xml_buffer, uro_ifc_boundary_surface_attribute{}.uro_ifc_wall_standard_case_uro_element_type xml_buffer, uro_ifc_boundary_surface_attribute{}.uro_ifc_wall_standard_case_uro_element_type_codeSpace xml_buffer, uro_ifc_boundary_surface_attribute{}.uro_ifc_wall_standard_case_uro_predefined_type xml_buffer, uro_ifc_boundary_surface_attribute{}.uro_ifc_wall_standard_case_uro_predefined_type_codeSpace xml_buffer, uro_ifc_boundary_surface_attribute{}.uro_ifc_wall_standard_case_uro_shape_type xml_buffer, uro_ifc_boundary_surface_attribute{}.uro_ifc_wall_standard_case_uro_shape_type_codeSpace xml_buffer, uro_ifc_boundary_surface_attribute{}.uro_ifc_wall_standard_case_uro_number_of_riser xml_int64, uro_ifc_boundary_surface_attribute{}.uro_ifc_wall_standard_case_uro_number_of_treads xml_int64, uro_ifc_boundary_surface_attribute{}.uro_ifc_wall_standard_case_uro_riser_height xml_int64, uro_ifc_boundary_surface_attribute{}.uro_ifc_wall_standard_case_uro_tread_length xml_int64, uro_ifc_boundary_surface_attribute{}.uro_ifc_wall_standard_case_uro_operation_type xml_char(11), uro_ifc_boundary_surface_attribute{}.uro_ifc_wall_standard_case_uro_capacity_by_weight xml_real64, uro_ifc_boundary_surface_attribute{}.uro_ifc_wall_standard_case_uro_capacity_by_weight_units xml_buffer, uro_ifc_boundary_surface_attribute{}.uro_ifc_wall_standard_case_uro_capacity_by_number xml_int64, uro_ifc_boundary_surface_attribute{}.uro_ifc_wall_standard_case_uro_nominal_length xml_real64, uro_ifc_boundary_surface_attribute{}.uro_ifc_wall_standard_case_uro_nominal_length_units xml_buffer, uro_ifc_boundary_surface_attribute{}.uro_ifc_wall_standard_case_uro_nominal_width xml_real64, uro_ifc_boundary_surface_attribute{}.uro_ifc_wall_standard_case_uro_nominal_width_units xml_buffer, uro_ifc_boundary_surface_attribute{}.uro_ifc_wall_standard_case_uro_nominal_height xml_real64, uro_ifc_boundary_surface_attribute{}.uro_ifc_wall_standard_case_uro_nominal_height_units xml_buffer, uro_ifc_boundary_surface_attribute{}.uro_ifc_wall_standard_case_uro_gross_foot_print_area xml_real64, uro_ifc_boundary_surface_attribute{}.uro_ifc_wall_standard_case_uro_gross_foot_print_area_units xml_buffer,
      uro_ifc_boundary_surface_attribute{}.uro_ifc_wall_standard_case_uro_net_foot_print_area xml_real64, uro_ifc_boundary_surface_attribute{}.uro_ifc_wall_standard_case_uro_net_foot_print_area_units xml_buffer, uro_ifc_boundary_surface_attribute{}.uro_ifc_wall_standard_case_uro_gross_side_area xml_real64, uro_ifc_boundary_surface_attribute{}.uro_ifc_wall_standard_case_uro_gross_side_area_units xml_buffer, uro_ifc_boundary_surface_attribute{}.uro_ifc_wall_standard_case_uro_net_side_area xml_real64, uro_ifc_boundary_surface_attribute{}.uro_ifc_wall_standard_case_uro_net_side_area_units xml_buffer, uro_ifc_boundary_surface_attribute{}.uro_ifc_wall_standard_case_uro_gross_side_area_left xml_real64, uro_ifc_boundary_surface_attribute{}.uro_ifc_wall_standard_case_uro_gross_side_area_left_units xml_buffer, uro_ifc_boundary_surface_attribute{}.uro_ifc_wall_standard_case_uro_net_side_area_left xml_real64, uro_ifc_boundary_surface_attribute{}.uro_ifc_wall_standard_case_uro_net_side_area_left_units xml_buffer, uro_ifc_boundary_surface_attribute{}.uro_ifc_wall_standard_case_uro_gross_side_area_right xml_real64, uro_ifc_boundary_surface_attribute{}.uro_ifc_wall_standard_case_uro_gross_side_area_right_units xml_buffer, uro_ifc_boundary_surface_attribute{}.uro_ifc_wall_standard_case_uro_net_side_area_right xml_real64, uro_ifc_boundary_surface_attribute{}.uro_ifc_wall_standard_case_uro_net_side_area_right_units xml_buffer, uro_ifc_boundary_surface_attribute{}.uro_ifc_wall_standard_case_uro_gross_volume xml_real64, uro_ifc_boundary_surface_attribute{}.uro_ifc_wall_standard_case_uro_gross_volume_units xml_buffer, uro_ifc_boundary_surface_attribute{}.uro_ifc_wall_standard_case_uro_net_volume xml_real64, uro_ifc_boundary_surface_attribute{}.uro_ifc_wall_standard_case_uro_net_volume_units xml_buffer, uro_ifc_boundary_surface_attribute{}.uro_ifc_window_uro_global_id xml_buffer, uro_ifc_boundary_surface_attribute{}.uro_ifc_window_uro_name xml_buffer, uro_ifc_boundary_surface_attribute{}.uro_ifc_window_uro_description xml_buffer, uro_ifc_boundary_surface_attribute{}.uro_ifc_window_uro_object_type xml_buffer, uro_ifc_boundary_surface_attribute{}.uro_ifc_window_uro_tag xml_buffer, uro_ifc_boundary_surface_attribute{}.uro_ifc_window_uro_element_type xml_buffer, uro_ifc_boundary_surface_attribute{}.uro_ifc_window_uro_element_type_codeSpace xml_buffer, uro_ifc_boundary_surface_attribute{}.uro_ifc_window_uro_predefined_type xml_buffer, uro_ifc_boundary_surface_attribute{}.uro_ifc_window_uro_predefined_type_codeSpace xml_buffer, uro_ifc_boundary_surface_attribute{}.uro_ifc_window_uro_shape_type xml_buffer, uro_ifc_boundary_surface_attribute{}.uro_ifc_window_uro_shape_type_codeSpace xml_buffer, uro_ifc_boundary_surface_attribute{}.uro_ifc_window_uro_number_of_riser xml_int64,
      uro_ifc_boundary_surface_attribute{}.uro_ifc_window_uro_number_of_treads xml_int64, uro_ifc_boundary_surface_attribute{}.uro_ifc_window_uro_riser_height xml_int64, uro_ifc_boundary_surface_attribute{}.uro_ifc_window_uro_tread_length xml_int64, uro_ifc_boundary_surface_attribute{}.uro_ifc_window_uro_operation_type xml_char(11), uro_ifc_boundary_surface_attribute{}.uro_ifc_window_uro_capacity_by_weight xml_real64, uro_ifc_boundary_surface_attribute{}.uro_ifc_window_uro_capacity_by_weight_units xml_buffer, uro_ifc_boundary_surface_attribute{}.uro_ifc_window_uro_capacity_by_number xml_int64, uro_ifc_boundary_surface_attribute{}.uro_ifc_window_uro_overall_height xml_real64, uro_ifc_boundary_surface_attribute{}.uro_ifc_window_uro_overall_height_units xml_buffer, uro_ifc_boundary_surface_attribute{}.uro_ifc_window_uro_overall_width xml_real64, uro_ifc_boundary_surface_attribute{}.uro_ifc_window_uro_overall_width_units xml_buffer
OuterCeilingSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, uro_ifc_boundary_surface_attribute{}.uro_ifc_building_uro_global_id xml_buffer, uro_ifc_boundary_surface_attribute{}.uro_ifc_building_uro_name xml_buffer, uro_ifc_boundary_surface_attribute{}.uro_ifc_building_uro_description xml_buffer, uro_ifc_boundary_surface_attribute{}.uro_ifc_building_uro_object_type xml_buffer, uro_ifc_boundary_surface_attribute{}.uro_ifc_building_uro_long_name xml_buffer, uro_ifc_boundary_surface_attribute{}.uro_ifc_building_uro_composition_type xml_char(7), uro_ifc_boundary_surface_attribute{}.uro_ifc_building_uro_elevation_of_ref_height xml_real64, uro_ifc_boundary_surface_attribute{}.uro_ifc_building_uro_elevation_of_ref_height_units xml_buffer, uro_ifc_boundary_surface_attribute{}.uro_ifc_building_uro_elevation_of_terrain xml_real64, uro_ifc_boundary_surface_attribute{}.uro_ifc_building_uro_elevation_of_terrain_units xml_buffer, uro_ifc_boundary_surface_attribute{}.uro_ifc_building_uro_building_address_xlink_href xml_buffer, uro_ifc_boundary_surface_attribute{}.uro_ifc_building_element_uro_global_id xml_buffer, uro_ifc_boundary_surface_attribute{}.uro_ifc_building_element_uro_name xml_buffer, uro_ifc_boundary_surface_attribute{}.uro_ifc_building_element_uro_description xml_buffer,
      uro_ifc_boundary_surface_attribute{}.uro_ifc_building_element_uro_object_type xml_buffer, uro_ifc_boundary_surface_attribute{}.uro_ifc_building_element_uro_tag xml_buffer, uro_ifc_boundary_surface_attribute{}.uro_ifc_building_element_uro_element_type xml_buffer, uro_ifc_boundary_surface_attribute{}.uro_ifc_building_element_uro_element_type_codeSpace xml_buffer, uro_ifc_boundary_surface_attribute{}.uro_ifc_building_element_uro_predefined_type xml_buffer, uro_ifc_boundary_surface_attribute{}.uro_ifc_building_element_uro_predefined_type_codeSpace xml_buffer, uro_ifc_boundary_surface_attribute{}.uro_ifc_building_element_uro_shape_type xml_buffer, uro_ifc_boundary_surface_attribute{}.uro_ifc_building_element_uro_shape_type_codeSpace xml_buffer, uro_ifc_boundary_surface_attribute{}.uro_ifc_building_element_uro_number_of_riser xml_int64, uro_ifc_boundary_surface_attribute{}.uro_ifc_building_element_uro_number_of_treads xml_int64, uro_ifc_boundary_surface_attribute{}.uro_ifc_building_element_uro_riser_height xml_int64, uro_ifc_boundary_surface_attribute{}.uro_ifc_building_element_uro_tread_length xml_int64, uro_ifc_boundary_surface_attribute{}.uro_ifc_building_element_uro_operation_type xml_char(11), uro_ifc_boundary_surface_attribute{}.uro_ifc_building_element_uro_capacity_by_weight xml_real64, uro_ifc_boundary_surface_attribute{}.uro_ifc_building_element_uro_capacity_by_weight_units xml_buffer, uro_ifc_boundary_surface_attribute{}.uro_ifc_building_element_uro_capacity_by_number xml_int64, uro_ifc_boundary_surface_attribute{}.uro_ifc_building_storey_uro_global_id xml_buffer, uro_ifc_boundary_surface_attribute{}.uro_ifc_building_storey_uro_name xml_buffer, uro_ifc_boundary_surface_attribute{}.uro_ifc_building_storey_uro_description xml_buffer, uro_ifc_boundary_surface_attribute{}.uro_ifc_building_storey_uro_object_type xml_buffer, uro_ifc_boundary_surface_attribute{}.uro_ifc_building_storey_uro_long_name xml_buffer, uro_ifc_boundary_surface_attribute{}.uro_ifc_building_storey_uro_composition_type xml_char(7), uro_ifc_boundary_surface_attribute{}.uro_ifc_building_storey_uro_elevation xml_real64, uro_ifc_boundary_surface_attribute{}.uro_ifc_building_storey_uro_elevation_units xml_buffer, uro_ifc_boundary_surface_attribute{}.uro_ifc_classification_reference_uro_location xml_buffer, uro_ifc_boundary_surface_attribute{}.uro_ifc_classification_reference_uro_item_reference xml_buffer, uro_ifc_boundary_surface_attribute{}.uro_ifc_classification_reference_uro_item_reference_codeSpace xml_buffer, uro_ifc_boundary_surface_attribute{}.uro_ifc_classification_reference_uro_name xml_buffer, uro_ifc_boundary_surface_attribute{}.uro_ifc_classification_reference_uro_name_codeSpace xml_buffer, uro_ifc_boundary_surface_attribute{}.uro_ifc_classification_reference_uro_reference_source_uro_ifc_classification_uro_source xml_buffer,
      uro_ifc_boundary_surface_attribute{}.uro_ifc_classification_reference_uro_reference_source_uro_ifc_classification_uro_edition xml_buffer, uro_ifc_boundary_surface_attribute{}.uro_ifc_classification_reference_uro_reference_source_uro_ifc_classification_uro_edition_date xml_date, uro_ifc_boundary_surface_attribute{}.uro_ifc_classification_reference_uro_reference_source_uro_ifc_classification_uro_name xml_buffer, uro_ifc_boundary_surface_attribute{}.uro_ifc_coordinate_reference_system_uro_name xml_buffer, uro_ifc_boundary_surface_attribute{}.uro_ifc_coordinate_reference_system_uro_description xml_buffer, uro_ifc_boundary_surface_attribute{}.uro_ifc_coordinate_reference_system_uro_geodetic_datum xml_buffer, uro_ifc_boundary_surface_attribute{}.uro_ifc_coordinate_reference_system_uro_vertical_datum xml_buffer, uro_ifc_boundary_surface_attribute{}.uro_ifc_curtain_wall_uro_global_id xml_buffer, uro_ifc_boundary_surface_attribute{}.uro_ifc_curtain_wall_uro_name xml_buffer, uro_ifc_boundary_surface_attribute{}.uro_ifc_curtain_wall_uro_description xml_buffer, uro_ifc_boundary_surface_attribute{}.uro_ifc_curtain_wall_uro_object_type xml_buffer, uro_ifc_boundary_surface_attribute{}.uro_ifc_curtain_wall_uro_tag xml_buffer, uro_ifc_boundary_surface_attribute{}.uro_ifc_curtain_wall_uro_element_type xml_buffer, uro_ifc_boundary_surface_attribute{}.uro_ifc_curtain_wall_uro_element_type_codeSpace xml_buffer, uro_ifc_boundary_surface_attribute{}.uro_ifc_curtain_wall_uro_predefined_type xml_buffer, uro_ifc_boundary_surface_attribute{}.uro_ifc_curtain_wall_uro_predefined_type_codeSpace xml_buffer, uro_ifc_boundary_surface_attribute{}.uro_ifc_curtain_wall_uro_shape_type xml_buffer, uro_ifc_boundary_surface_attribute{}.uro_ifc_curtain_wall_uro_shape_type_codeSpace xml_buffer, uro_ifc_boundary_surface_attribute{}.uro_ifc_curtain_wall_uro_number_of_riser xml_int64, uro_ifc_boundary_surface_attribute{}.uro_ifc_curtain_wall_uro_number_of_treads xml_int64, uro_ifc_boundary_surface_attribute{}.uro_ifc_curtain_wall_uro_riser_height xml_int64, uro_ifc_boundary_surface_attribute{}.uro_ifc_curtain_wall_uro_tread_length xml_int64, uro_ifc_boundary_surface_attribute{}.uro_ifc_curtain_wall_uro_operation_type xml_char(11), uro_ifc_boundary_surface_attribute{}.uro_ifc_curtain_wall_uro_capacity_by_weight xml_real64, uro_ifc_boundary_surface_attribute{}.uro_ifc_curtain_wall_uro_capacity_by_weight_units xml_buffer, uro_ifc_boundary_surface_attribute{}.uro_ifc_curtain_wall_uro_capacity_by_number xml_int64, uro_ifc_boundary_surface_attribute{}.uro_ifc_door_uro_global_id xml_buffer, uro_ifc_boundary_surface_attribute{}.uro_ifc_door_uro_name xml_buffer, uro_ifc_boundary_surface_attribute{}.uro_ifc_door_uro_description xml_buffer, uro_ifc_boundary_surface_attribute{}.uro_ifc_door_uro_object_type xml_buffer,
      uro_ifc_boundary_surface_attribute{}.uro_ifc_door_uro_tag xml_buffer, uro_ifc_boundary_surface_attribute{}.uro_ifc_door_uro_element_type xml_buffer, uro_ifc_boundary_surface_attribute{}.uro_ifc_door_uro_element_type_codeSpace xml_buffer, uro_ifc_boundary_surface_attribute{}.uro_ifc_door_uro_predefined_type xml_buffer, uro_ifc_boundary_surface_attribute{}.uro_ifc_door_uro_predefined_type_codeSpace xml_buffer, uro_ifc_boundary_surface_attribute{}.uro_ifc_door_uro_shape_type xml_buffer, uro_ifc_boundary_surface_attribute{}.uro_ifc_door_uro_shape_type_codeSpace xml_buffer, uro_ifc_boundary_surface_attribute{}.uro_ifc_door_uro_number_of_riser xml_int64, uro_ifc_boundary_surface_attribute{}.uro_ifc_door_uro_number_of_treads xml_int64, uro_ifc_boundary_surface_attribute{}.uro_ifc_door_uro_riser_height xml_int64, uro_ifc_boundary_surface_attribute{}.uro_ifc_door_uro_tread_length xml_int64, uro_ifc_boundary_surface_attribute{}.uro_ifc_door_uro_operation_type xml_char(11), uro_ifc_boundary_surface_attribute{}.uro_ifc_door_uro_capacity_by_weight xml_real64, uro_ifc_boundary_surface_attribute{}.uro_ifc_door_uro_capacity_by_weight_units xml_buffer, uro_ifc_boundary_surface_attribute{}.uro_ifc_door_uro_capacity_by_number xml_int64, uro_ifc_boundary_surface_attribute{}.uro_ifc_door_uro_overall_height xml_real64, uro_ifc_boundary_surface_attribute{}.uro_ifc_door_uro_overall_height_units xml_buffer, uro_ifc_boundary_surface_attribute{}.uro_ifc_door_uro_overall_width xml_real64, uro_ifc_boundary_surface_attribute{}.uro_ifc_door_uro_overall_width_units xml_buffer, uro_ifc_boundary_surface_attribute{}.uro_ifc_furnishing_element_uro_global_id xml_buffer, uro_ifc_boundary_surface_attribute{}.uro_ifc_furnishing_element_uro_name xml_buffer, uro_ifc_boundary_surface_attribute{}.uro_ifc_furnishing_element_uro_description xml_buffer, uro_ifc_boundary_surface_attribute{}.uro_ifc_furnishing_element_uro_object_type xml_buffer, uro_ifc_boundary_surface_attribute{}.uro_ifc_furnishing_element_uro_tag xml_buffer, uro_ifc_boundary_surface_attribute{}.uro_ifc_map_conversion_uro_source_crs_uro_crs_uro_ifc_projected_crs_uro_name xml_buffer, uro_ifc_boundary_surface_attribute{}.uro_ifc_map_conversion_uro_source_crs_uro_crs_uro_ifc_projected_crs_uro_description xml_buffer, uro_ifc_boundary_surface_attribute{}.uro_ifc_map_conversion_uro_source_crs_uro_crs_uro_ifc_projected_crs_uro_geodetic_datum xml_buffer, uro_ifc_boundary_surface_attribute{}.uro_ifc_map_conversion_uro_source_crs_uro_crs_uro_ifc_projected_crs_uro_vertical_datum xml_buffer, uro_ifc_boundary_surface_attribute{}.uro_ifc_map_conversion_uro_source_crs_uro_crs_uro_ifc_projected_crs_uro_map_unit xml_buffer, uro_ifc_boundary_surface_attribute{}.uro_ifc_map_conversion_uro_source_crs_uro_crs_uro_ifc_projected_crs_uro_map_projection xml_buffer,
      uro_ifc_boundary_surface_attribute{}.uro_ifc_map_conversion_uro_source_crs_uro_crs_uro_ifc_projected_crs_uro_map_zone xml_buffer, uro_ifc_boundary_surface_attribute{}.uro_ifc_map_conversion_uro_source_crs_uro_crs_uro_ifc_coordinate_reference_system_uro_name xml_buffer, uro_ifc_boundary_surface_attribute{}.uro_ifc_map_conversion_uro_source_crs_uro_crs_uro_ifc_coordinate_reference_system_uro_description xml_buffer, uro_ifc_boundary_surface_attribute{}.uro_ifc_map_conversion_uro_source_crs_uro_crs_uro_ifc_coordinate_reference_system_uro_geodetic_datum xml_buffer, uro_ifc_boundary_surface_attribute{}.uro_ifc_map_conversion_uro_source_crs_uro_crs_uro_ifc_coordinate_reference_system_uro_vertical_datum xml_buffer, uro_ifc_boundary_surface_attribute{}.uro_ifc_map_conversion_uro_source_crs_uro_context_uro_ifc_geometric_representation_context_uro_context_identifier xml_buffer, uro_ifc_boundary_surface_attribute{}.uro_ifc_map_conversion_uro_source_crs_uro_context_uro_ifc_geometric_representation_context_uro_context_type xml_buffer, uro_ifc_boundary_surface_attribute{}.uro_ifc_map_conversion_uro_source_crs_uro_context_uro_ifc_geometric_representation_context_uro_coordinate_space_dimension xml_int64, uro_ifc_boundary_surface_attribute{}.uro_ifc_map_conversion_uro_source_crs_uro_context_uro_ifc_geometric_representation_context_uro_precision xml_real64, uro_ifc_boundary_surface_attribute{}.uro_ifc_map_conversion_uro_source_crs_uro_context_uro_ifc_geometric_representation_context_uro_true_north xml_real64, uro_ifc_boundary_surface_attribute{}.uro_ifc_map_conversion_uro_target_crs_uro_ifc_projected_crs_uro_name xml_buffer, uro_ifc_boundary_surface_attribute{}.uro_ifc_map_conversion_uro_target_crs_uro_ifc_projected_crs_uro_description xml_buffer, uro_ifc_boundary_surface_attribute{}.uro_ifc_map_conversion_uro_target_crs_uro_ifc_projected_crs_uro_geodetic_datum xml_buffer, uro_ifc_boundary_surface_attribute{}.uro_ifc_map_conversion_uro_target_crs_uro_ifc_projected_crs_uro_vertical_datum xml_buffer, uro_ifc_boundary_surface_attribute{}.uro_ifc_map_conversion_uro_target_crs_uro_ifc_projected_crs_uro_map_unit xml_buffer, uro_ifc_boundary_surface_attribute{}.uro_ifc_map_conversion_uro_target_crs_uro_ifc_projected_crs_uro_map_projection xml_buffer, uro_ifc_boundary_surface_attribute{}.uro_ifc_map_conversion_uro_target_crs_uro_ifc_projected_crs_uro_map_zone xml_buffer, uro_ifc_boundary_surface_attribute{}.uro_ifc_map_conversion_uro_target_crs_uro_ifc_coordinate_reference_system_uro_name xml_buffer, uro_ifc_boundary_surface_attribute{}.uro_ifc_map_conversion_uro_target_crs_uro_ifc_coordinate_reference_system_uro_description xml_buffer, uro_ifc_boundary_surface_attribute{}.uro_ifc_map_conversion_uro_target_crs_uro_ifc_coordinate_reference_system_uro_geodetic_datum xml_buffer, uro_ifc_boundary_surface_attribute{}.uro_ifc_map_conversion_uro_target_crs_uro_ifc_coordinate_reference_system_uro_vertical_datum xml_buffer, uro_ifc_boundary_surface_attribute{}.uro_ifc_map_conversion_uro_eastings xml_buffer, uro_ifc_boundary_surface_attribute{}.uro_ifc_map_conversion_uro_northings xml_buffer, uro_ifc_boundary_surface_attribute{}.uro_ifc_map_conversion_uro_orthogonal_height xml_real64, uro_ifc_boundary_surface_attribute{}.uro_ifc_map_conversion_uro_orthogonal_height_units xml_buffer, uro_ifc_boundary_surface_attribute{}.uro_ifc_map_conversion_uro_x_axis_abscissa xml_real64, uro_ifc_boundary_surface_attribute{}.uro_ifc_map_conversion_uro_x_axis_ordinate xml_real64, uro_ifc_boundary_surface_attribute{}.uro_ifc_map_conversion_uro_scale xml_real64, uro_ifc_boundary_surface_attribute{}.uro_ifc_opening_element_uro_global_id xml_buffer, uro_ifc_boundary_surface_attribute{}.uro_ifc_opening_element_uro_name xml_buffer,
      uro_ifc_boundary_surface_attribute{}.uro_ifc_opening_element_uro_description xml_buffer, uro_ifc_boundary_surface_attribute{}.uro_ifc_opening_element_uro_object_type xml_buffer, uro_ifc_boundary_surface_attribute{}.uro_ifc_opening_element_uro_tag xml_buffer, uro_ifc_boundary_surface_attribute{}.uro_ifc_opening_element_uro_nominal_area xml_real64, uro_ifc_boundary_surface_attribute{}.uro_ifc_opening_element_uro_nominal_area_units xml_buffer, uro_ifc_boundary_surface_attribute{}.uro_ifc_opening_element_uro_nominal_volume xml_real64, uro_ifc_boundary_surface_attribute{}.uro_ifc_opening_element_uro_nominal_volume_units xml_buffer, uro_ifc_boundary_surface_attribute{}.uro_ifc_project_uro_global_id xml_buffer, uro_ifc_boundary_surface_attribute{}.uro_ifc_project_uro_name xml_buffer, uro_ifc_boundary_surface_attribute{}.uro_ifc_project_uro_description xml_buffer, uro_ifc_boundary_surface_attribute{}.uro_ifc_project_uro_object_type xml_buffer, uro_ifc_boundary_surface_attribute{}.uro_ifc_project_uro_long_name xml_buffer, uro_ifc_boundary_surface_attribute{}.uro_ifc_project_uro_phase xml_buffer, uro_ifc_boundary_surface_attribute{}.uro_ifc_project_uro_representation_contexts_uro_ifc_geometric_representation_context_uro_context_identifier xml_buffer, uro_ifc_boundary_surface_attribute{}.uro_ifc_project_uro_representation_contexts_uro_ifc_geometric_representation_context_uro_context_type xml_buffer, uro_ifc_boundary_surface_attribute{}.uro_ifc_project_uro_representation_contexts_uro_ifc_geometric_representation_context_uro_coordinate_space_dimension xml_int64, uro_ifc_boundary_surface_attribute{}.uro_ifc_project_uro_representation_contexts_uro_ifc_geometric_representation_context_uro_precision xml_real64, uro_ifc_boundary_surface_attribute{}.uro_ifc_project_uro_representation_contexts_uro_ifc_geometric_representation_context_uro_true_north xml_real64, uro_ifc_boundary_surface_attribute{}.uro_ifc_project_uro_units_in_context{}.uro_ifc_unit_uro_dimensions xml_int64, uro_ifc_boundary_surface_attribute{}.uro_ifc_project_uro_units_in_context{}.uro_ifc_unit_uro_unit_type xml_char(28), uro_ifc_boundary_surface_attribute{}.uro_ifc_project_uro_units_in_context{}.uro_ifc_unit_uro_perfix xml_buffer, uro_ifc_boundary_surface_attribute{}.uro_ifc_project_uro_units_in_context{}.uro_ifc_unit_uro_name xml_buffer, uro_ifc_boundary_surface_attribute{}.uro_ifc_projected_crs_uro_name xml_buffer, uro_ifc_boundary_surface_attribute{}.uro_ifc_projected_crs_uro_description xml_buffer, uro_ifc_boundary_surface_attribute{}.uro_ifc_projected_crs_uro_geodetic_datum xml_buffer, uro_ifc_boundary_surface_attribute{}.uro_ifc_projected_crs_uro_vertical_datum xml_buffer, uro_ifc_boundary_surface_attribute{}.uro_ifc_projected_crs_uro_map_unit xml_buffer, uro_ifc_boundary_surface_attribute{}.uro_ifc_projected_crs_uro_map_projection xml_buffer, uro_ifc_boundary_surface_attribute{}.uro_ifc_projected_crs_uro_map_zone xml_buffer, uro_ifc_boundary_surface_attribute{}.uro_ifc_pset_building_common_uro_building_id xml_real64,
      uro_ifc_boundary_surface_attribute{}.uro_ifc_pset_building_common_uro_building_id_units xml_buffer, uro_ifc_boundary_surface_attribute{}.uro_ifc_pset_building_common_uro_is_permanent_id xml_real64, uro_ifc_boundary_surface_attribute{}.uro_ifc_pset_building_common_uro_is_permanent_id_units xml_buffer, uro_ifc_boundary_surface_attribute{}.uro_ifc_pset_building_common_uro_main_fire_use xml_buffer, uro_ifc_boundary_surface_attribute{}.uro_ifc_pset_building_common_uro_ancillary_fire_use xml_buffer, uro_ifc_boundary_surface_attribute{}.uro_ifc_pset_building_common_uro_sprinkler_protection xml_boolean, uro_ifc_boundary_surface_attribute{}.uro_ifc_pset_building_common_uro_sprinkler_protection_automatic xml_boolean, uro_ifc_boundary_surface_attribute{}.uro_ifc_pset_building_common_uro_occupancy_type xml_buffer, uro_ifc_boundary_surface_attribute{}.uro_ifc_pset_building_common_uro_occupancy_type_codeSpace xml_buffer, uro_ifc_boundary_surface_attribute{}.uro_ifc_pset_building_common_uro_gross_planned_area xml_real64, uro_ifc_boundary_surface_attribute{}.uro_ifc_pset_building_common_uro_gross_planned_area_units xml_buffer, uro_ifc_boundary_surface_attribute{}.uro_ifc_pset_building_common_uro_number_of_storeys xml_int64, uro_ifc_boundary_surface_attribute{}.uro_ifc_pset_building_common_uro_year_of_construction xml_buffer, uro_ifc_boundary_surface_attribute{}.uro_ifc_pset_building_common_uro_is_landmarked xml_boolean, uro_ifc_boundary_surface_attribute{}.uro_ifc_pset_door_common_uro_reference xml_buffer, uro_ifc_boundary_surface_attribute{}.uro_ifc_pset_door_common_uro_acoustic_rating xml_buffer, uro_ifc_boundary_surface_attribute{}.uro_ifc_pset_door_common_uro_firerating xml_buffer, uro_ifc_boundary_surface_attribute{}.uro_ifc_pset_door_common_uro_security_rating xml_buffer, uro_ifc_boundary_surface_attribute{}.uro_ifc_pset_door_common_uro_is_external xml_boolean, uro_ifc_boundary_surface_attribute{}.uro_ifc_pset_door_common_uro_infiltration xml_real64, uro_ifc_boundary_surface_attribute{}.uro_ifc_pset_door_common_uro_thermal_transmittance xml_real64, uro_ifc_boundary_surface_attribute{}.uro_ifc_pset_door_common_uro_glazing_area_fraction xml_real64, uro_ifc_boundary_surface_attribute{}.uro_ifc_pset_door_common_uro_handicap_accessible xml_real64, uro_ifc_boundary_surface_attribute{}.uro_ifc_pset_door_common_uro_fire_exit xml_boolean, uro_ifc_boundary_surface_attribute{}.uro_ifc_pset_door_common_uro_self_closing xml_real64, uro_ifc_boundary_surface_attribute{}.uro_ifc_pset_door_common_uro_smoke_stop xml_boolean, uro_ifc_boundary_surface_attribute{}.uro_ifc_pset_opening_element_common_uro_reference xml_buffer, uro_ifc_boundary_surface_attribute{}.uro_ifc_pset_opening_element_common_uro_purpose xml_buffer, uro_ifc_boundary_surface_attribute{}.uro_ifc_pset_opening_element_common_uro_fire_exit xml_boolean, uro_ifc_boundary_surface_attribute{}.uro_ifc_pset_opening_element_common_uro_protected_opening xml_boolean,
      uro_ifc_boundary_surface_attribute{}.uro_ifc_pset_opening_element_common_uro_parallel_jambs xml_boolean, uro_ifc_boundary_surface_attribute{}.uro_ifc_pset_site_common_uro_buildable_area xml_real64, uro_ifc_boundary_surface_attribute{}.uro_ifc_pset_site_common_uro_buildable_area_units xml_buffer, uro_ifc_boundary_surface_attribute{}.uro_ifc_pset_site_common_uro_total_area xml_real64, uro_ifc_boundary_surface_attribute{}.uro_ifc_pset_site_common_uro_total_area_units xml_buffer, uro_ifc_boundary_surface_attribute{}.uro_ifc_pset_site_common_uro_building_height_limit xml_real64, uro_ifc_boundary_surface_attribute{}.uro_ifc_pset_site_common_uro_building_height_limit_units xml_buffer, uro_ifc_boundary_surface_attribute{}.uro_ifc_pset_space_common_uro_reference xml_buffer, uro_ifc_boundary_surface_attribute{}.uro_ifc_pset_space_common_uro_category xml_buffer, uro_ifc_boundary_surface_attribute{}.uro_ifc_pset_space_common_uro_category_codeSpace xml_buffer, uro_ifc_boundary_surface_attribute{}.uro_ifc_pset_space_common_uro_floor_covering xml_buffer, uro_ifc_boundary_surface_attribute{}.uro_ifc_pset_space_common_uro_wall_covering xml_buffer, uro_ifc_boundary_surface_attribute{}.uro_ifc_pset_space_common_uro_ceiling_covering xml_buffer, uro_ifc_boundary_surface_attribute{}.uro_ifc_pset_space_common_uro_skirting_covering xml_buffer, uro_ifc_boundary_surface_attribute{}.uro_ifc_pset_space_common_uro_gross_planned_area xml_real64, uro_ifc_boundary_surface_attribute{}.uro_ifc_pset_space_common_uro_gross_planned_area_units xml_buffer, uro_ifc_boundary_surface_attribute{}.uro_ifc_pset_space_common_uro_net_planned_area xml_real64, uro_ifc_boundary_surface_attribute{}.uro_ifc_pset_space_common_uro_net_planned_area_units xml_buffer, uro_ifc_boundary_surface_attribute{}.uro_ifc_pset_space_common_uro_publicly_accessible xml_boolean, uro_ifc_boundary_surface_attribute{}.uro_ifc_pset_space_common_uro_handicap_accessible xml_boolean, uro_ifc_boundary_surface_attribute{}.uro_ifc_pset_space_common_uro_concealed_flooring xml_boolean, uro_ifc_boundary_surface_attribute{}.uro_ifc_pset_space_common_uro_concealed_ceiling xml_boolean, uro_ifc_boundary_surface_attribute{}.uro_ifc_pset_window_common_uro_reference xml_buffer, uro_ifc_boundary_surface_attribute{}.uro_ifc_pset_window_common_uro_acoustic_rating xml_buffer, uro_ifc_boundary_surface_attribute{}.uro_ifc_pset_window_common_uro_firerating xml_buffer, uro_ifc_boundary_surface_attribute{}.uro_ifc_pset_window_common_uro_security_rating xml_buffer, uro_ifc_boundary_surface_attribute{}.uro_ifc_pset_window_common_uro_is_external xml_boolean, uro_ifc_boundary_surface_attribute{}.uro_ifc_pset_window_common_uro_infiltration xml_real64, uro_ifc_boundary_surface_attribute{}.uro_ifc_pset_window_common_uro_thermal_transmittance xml_real64, uro_ifc_boundary_surface_attribute{}.uro_ifc_pset_window_common_uro_glazing_area_fraction xml_real64,
      uro_ifc_boundary_surface_attribute{}.uro_ifc_pset_window_common_uro_smoke_stop xml_boolean, uro_ifc_boundary_surface_attribute{}.uro_ifc_site_uro_global_id xml_buffer, uro_ifc_boundary_surface_attribute{}.uro_ifc_site_uro_name xml_buffer, uro_ifc_boundary_surface_attribute{}.uro_ifc_site_uro_description xml_buffer, uro_ifc_boundary_surface_attribute{}.uro_ifc_site_uro_object_type xml_buffer, uro_ifc_boundary_surface_attribute{}.uro_ifc_site_uro_long_name xml_buffer, uro_ifc_boundary_surface_attribute{}.uro_ifc_site_uro_composition_type xml_char(7), uro_ifc_boundary_surface_attribute{}.uro_ifc_site_uro_ref_longitude xml_real64, uro_ifc_boundary_surface_attribute{}.uro_ifc_site_uro_ref_latitude xml_real64, uro_ifc_boundary_surface_attribute{}.uro_ifc_site_uro_ref_elevation xml_real64, uro_ifc_boundary_surface_attribute{}.uro_ifc_site_uro_ref_elevation_units xml_buffer, uro_ifc_boundary_surface_attribute{}.uro_ifc_site_uro_land_title_number xml_buffer, uro_ifc_boundary_surface_attribute{}.uro_ifc_site_uro_site_address_xlink_href xml_buffer, uro_ifc_boundary_surface_attribute{}.uro_ifc_space_uro_global_id xml_buffer, uro_ifc_boundary_surface_attribute{}.uro_ifc_space_uro_name xml_buffer, uro_ifc_boundary_surface_attribute{}.uro_ifc_space_uro_description xml_buffer, uro_ifc_boundary_surface_attribute{}.uro_ifc_space_uro_object_type xml_buffer, uro_ifc_boundary_surface_attribute{}.uro_ifc_space_uro_long_name xml_buffer, uro_ifc_boundary_surface_attribute{}.uro_ifc_space_uro_composition_type xml_char(7), uro_ifc_boundary_surface_attribute{}.uro_ifc_space_uro_interioror_exterior_space xml_char(10), uro_ifc_boundary_surface_attribute{}.uro_ifc_space_uro_elevation_with_flooring xml_real64, uro_ifc_boundary_surface_attribute{}.uro_ifc_space_uro_elevation_with_flooring_units xml_buffer, uro_ifc_boundary_surface_attribute{}.uro_ifc_space_base_quantity_uro_nominal_height xml_real64, uro_ifc_boundary_surface_attribute{}.uro_ifc_space_base_quantity_uro_nominal_height_units xml_buffer, uro_ifc_boundary_surface_attribute{}.uro_ifc_space_base_quantity_uro_clear_height xml_real64, uro_ifc_boundary_surface_attribute{}.uro_ifc_space_base_quantity_uro_clear_height_units xml_buffer, uro_ifc_boundary_surface_attribute{}.uro_ifc_space_base_quantity_uro_finish_ceiling_height xml_real64, uro_ifc_boundary_surface_attribute{}.uro_ifc_space_base_quantity_uro_finish_ceiling_height_units xml_buffer, uro_ifc_boundary_surface_attribute{}.uro_ifc_space_base_quantity_uro_gross_perimeter xml_real64, uro_ifc_boundary_surface_attribute{}.uro_ifc_space_base_quantity_uro_gross_perimeter_units xml_buffer,
      uro_ifc_boundary_surface_attribute{}.uro_ifc_space_base_quantity_uro_net_perimeter xml_real64, uro_ifc_boundary_surface_attribute{}.uro_ifc_space_base_quantity_uro_net_perimeter_units xml_buffer, uro_ifc_boundary_surface_attribute{}.uro_ifc_space_base_quantity_uro_gross_ceiling_area xml_real64, uro_ifc_boundary_surface_attribute{}.uro_ifc_space_base_quantity_uro_gross_ceiling_area_units xml_buffer, uro_ifc_boundary_surface_attribute{}.uro_ifc_space_base_quantity_uro_gross_floor_area xml_real64, uro_ifc_boundary_surface_attribute{}.uro_ifc_space_base_quantity_uro_gross_floor_area_units xml_buffer, uro_ifc_boundary_surface_attribute{}.uro_ifc_space_base_quantity_uro_net_ceiling_area xml_real64, uro_ifc_boundary_surface_attribute{}.uro_ifc_space_base_quantity_uro_net_ceiling_area_units xml_buffer, uro_ifc_boundary_surface_attribute{}.uro_ifc_space_base_quantity_uro_net_floor_area xml_real64, uro_ifc_boundary_surface_attribute{}.uro_ifc_space_base_quantity_uro_net_floor_area_units xml_buffer, uro_ifc_boundary_surface_attribute{}.uro_ifc_space_base_quantity_uro_gross_wall_area xml_real64, uro_ifc_boundary_surface_attribute{}.uro_ifc_space_base_quantity_uro_gross_wall_area_units xml_buffer, uro_ifc_boundary_surface_attribute{}.uro_ifc_space_base_quantity_uro_net_wall_area xml_real64, uro_ifc_boundary_surface_attribute{}.uro_ifc_space_base_quantity_uro_net_wall_area_units xml_buffer, uro_ifc_boundary_surface_attribute{}.uro_ifc_space_base_quantity_uro_gross_volume xml_real64, uro_ifc_boundary_surface_attribute{}.uro_ifc_space_base_quantity_uro_gross_volume_units xml_buffer, uro_ifc_boundary_surface_attribute{}.uro_ifc_space_base_quantity_uro_net_volume xml_real64, uro_ifc_boundary_surface_attribute{}.uro_ifc_space_base_quantity_uro_net_volume_units xml_buffer, uro_ifc_boundary_surface_attribute{}.uro_ifc_wall_uro_global_id xml_buffer, uro_ifc_boundary_surface_attribute{}.uro_ifc_wall_uro_name xml_buffer, uro_ifc_boundary_surface_attribute{}.uro_ifc_wall_uro_description xml_buffer, uro_ifc_boundary_surface_attribute{}.uro_ifc_wall_uro_object_type xml_buffer, uro_ifc_boundary_surface_attribute{}.uro_ifc_wall_uro_tag xml_buffer, uro_ifc_boundary_surface_attribute{}.uro_ifc_wall_uro_element_type xml_buffer, uro_ifc_boundary_surface_attribute{}.uro_ifc_wall_uro_element_type_codeSpace xml_buffer, uro_ifc_boundary_surface_attribute{}.uro_ifc_wall_uro_predefined_type xml_buffer, uro_ifc_boundary_surface_attribute{}.uro_ifc_wall_uro_predefined_type_codeSpace xml_buffer, uro_ifc_boundary_surface_attribute{}.uro_ifc_wall_uro_shape_type xml_buffer, uro_ifc_boundary_surface_attribute{}.uro_ifc_wall_uro_shape_type_codeSpace xml_buffer, uro_ifc_boundary_surface_attribute{}.uro_ifc_wall_uro_number_of_riser xml_int64,
      uro_ifc_boundary_surface_attribute{}.uro_ifc_wall_uro_number_of_treads xml_int64, uro_ifc_boundary_surface_attribute{}.uro_ifc_wall_uro_riser_height xml_int64, uro_ifc_boundary_surface_attribute{}.uro_ifc_wall_uro_tread_length xml_int64, uro_ifc_boundary_surface_attribute{}.uro_ifc_wall_uro_operation_type xml_char(11), uro_ifc_boundary_surface_attribute{}.uro_ifc_wall_uro_capacity_by_weight xml_real64, uro_ifc_boundary_surface_attribute{}.uro_ifc_wall_uro_capacity_by_weight_units xml_buffer, uro_ifc_boundary_surface_attribute{}.uro_ifc_wall_uro_capacity_by_number xml_int64, uro_ifc_boundary_surface_attribute{}.uro_ifc_wall_uro_nominal_length xml_real64, uro_ifc_boundary_surface_attribute{}.uro_ifc_wall_uro_nominal_length_units xml_buffer, uro_ifc_boundary_surface_attribute{}.uro_ifc_wall_uro_nominal_width xml_real64, uro_ifc_boundary_surface_attribute{}.uro_ifc_wall_uro_nominal_width_units xml_buffer, uro_ifc_boundary_surface_attribute{}.uro_ifc_wall_uro_nominal_height xml_real64, uro_ifc_boundary_surface_attribute{}.uro_ifc_wall_uro_nominal_height_units xml_buffer, uro_ifc_boundary_surface_attribute{}.uro_ifc_wall_uro_gross_foot_print_area xml_real64, uro_ifc_boundary_surface_attribute{}.uro_ifc_wall_uro_gross_foot_print_area_units xml_buffer, uro_ifc_boundary_surface_attribute{}.uro_ifc_wall_uro_net_foot_print_area xml_real64, uro_ifc_boundary_surface_attribute{}.uro_ifc_wall_uro_net_foot_print_area_units xml_buffer, uro_ifc_boundary_surface_attribute{}.uro_ifc_wall_uro_gross_side_area xml_real64, uro_ifc_boundary_surface_attribute{}.uro_ifc_wall_uro_gross_side_area_units xml_buffer, uro_ifc_boundary_surface_attribute{}.uro_ifc_wall_uro_net_side_area xml_real64, uro_ifc_boundary_surface_attribute{}.uro_ifc_wall_uro_net_side_area_units xml_buffer, uro_ifc_boundary_surface_attribute{}.uro_ifc_wall_uro_gross_side_area_left xml_real64, uro_ifc_boundary_surface_attribute{}.uro_ifc_wall_uro_gross_side_area_left_units xml_buffer, uro_ifc_boundary_surface_attribute{}.uro_ifc_wall_uro_net_side_area_left xml_real64, uro_ifc_boundary_surface_attribute{}.uro_ifc_wall_uro_net_side_area_left_units xml_buffer, uro_ifc_boundary_surface_attribute{}.uro_ifc_wall_uro_gross_side_area_right xml_real64, uro_ifc_boundary_surface_attribute{}.uro_ifc_wall_uro_gross_side_area_right_units xml_buffer, uro_ifc_boundary_surface_attribute{}.uro_ifc_wall_uro_net_side_area_right xml_real64, uro_ifc_boundary_surface_attribute{}.uro_ifc_wall_uro_net_side_area_right_units xml_buffer, uro_ifc_boundary_surface_attribute{}.uro_ifc_wall_uro_gross_volume xml_real64,
      uro_ifc_boundary_surface_attribute{}.uro_ifc_wall_uro_gross_volume_units xml_buffer, uro_ifc_boundary_surface_attribute{}.uro_ifc_wall_uro_net_volume xml_real64, uro_ifc_boundary_surface_attribute{}.uro_ifc_wall_uro_net_volume_units xml_buffer, uro_ifc_boundary_surface_attribute{}.uro_ifc_wall_standard_case_uro_global_id xml_buffer, uro_ifc_boundary_surface_attribute{}.uro_ifc_wall_standard_case_uro_name xml_buffer, uro_ifc_boundary_surface_attribute{}.uro_ifc_wall_standard_case_uro_description xml_buffer, uro_ifc_boundary_surface_attribute{}.uro_ifc_wall_standard_case_uro_object_type xml_buffer, uro_ifc_boundary_surface_attribute{}.uro_ifc_wall_standard_case_uro_tag xml_buffer, uro_ifc_boundary_surface_attribute{}.uro_ifc_wall_standard_case_uro_element_type xml_buffer, uro_ifc_boundary_surface_attribute{}.uro_ifc_wall_standard_case_uro_element_type_codeSpace xml_buffer, uro_ifc_boundary_surface_attribute{}.uro_ifc_wall_standard_case_uro_predefined_type xml_buffer, uro_ifc_boundary_surface_attribute{}.uro_ifc_wall_standard_case_uro_predefined_type_codeSpace xml_buffer, uro_ifc_boundary_surface_attribute{}.uro_ifc_wall_standard_case_uro_shape_type xml_buffer, uro_ifc_boundary_surface_attribute{}.uro_ifc_wall_standard_case_uro_shape_type_codeSpace xml_buffer, uro_ifc_boundary_surface_attribute{}.uro_ifc_wall_standard_case_uro_number_of_riser xml_int64, uro_ifc_boundary_surface_attribute{}.uro_ifc_wall_standard_case_uro_number_of_treads xml_int64, uro_ifc_boundary_surface_attribute{}.uro_ifc_wall_standard_case_uro_riser_height xml_int64, uro_ifc_boundary_surface_attribute{}.uro_ifc_wall_standard_case_uro_tread_length xml_int64, uro_ifc_boundary_surface_attribute{}.uro_ifc_wall_standard_case_uro_operation_type xml_char(11), uro_ifc_boundary_surface_attribute{}.uro_ifc_wall_standard_case_uro_capacity_by_weight xml_real64, uro_ifc_boundary_surface_attribute{}.uro_ifc_wall_standard_case_uro_capacity_by_weight_units xml_buffer, uro_ifc_boundary_surface_attribute{}.uro_ifc_wall_standard_case_uro_capacity_by_number xml_int64, uro_ifc_boundary_surface_attribute{}.uro_ifc_wall_standard_case_uro_nominal_length xml_real64, uro_ifc_boundary_surface_attribute{}.uro_ifc_wall_standard_case_uro_nominal_length_units xml_buffer, uro_ifc_boundary_surface_attribute{}.uro_ifc_wall_standard_case_uro_nominal_width xml_real64, uro_ifc_boundary_surface_attribute{}.uro_ifc_wall_standard_case_uro_nominal_width_units xml_buffer, uro_ifc_boundary_surface_attribute{}.uro_ifc_wall_standard_case_uro_nominal_height xml_real64, uro_ifc_boundary_surface_attribute{}.uro_ifc_wall_standard_case_uro_nominal_height_units xml_buffer, uro_ifc_boundary_surface_attribute{}.uro_ifc_wall_standard_case_uro_gross_foot_print_area xml_real64, uro_ifc_boundary_surface_attribute{}.uro_ifc_wall_standard_case_uro_gross_foot_print_area_units xml_buffer,
      uro_ifc_boundary_surface_attribute{}.uro_ifc_wall_standard_case_uro_net_foot_print_area xml_real64, uro_ifc_boundary_surface_attribute{}.uro_ifc_wall_standard_case_uro_net_foot_print_area_units xml_buffer, uro_ifc_boundary_surface_attribute{}.uro_ifc_wall_standard_case_uro_gross_side_area xml_real64, uro_ifc_boundary_surface_attribute{}.uro_ifc_wall_standard_case_uro_gross_side_area_units xml_buffer, uro_ifc_boundary_surface_attribute{}.uro_ifc_wall_standard_case_uro_net_side_area xml_real64, uro_ifc_boundary_surface_attribute{}.uro_ifc_wall_standard_case_uro_net_side_area_units xml_buffer, uro_ifc_boundary_surface_attribute{}.uro_ifc_wall_standard_case_uro_gross_side_area_left xml_real64, uro_ifc_boundary_surface_attribute{}.uro_ifc_wall_standard_case_uro_gross_side_area_left_units xml_buffer, uro_ifc_boundary_surface_attribute{}.uro_ifc_wall_standard_case_uro_net_side_area_left xml_real64, uro_ifc_boundary_surface_attribute{}.uro_ifc_wall_standard_case_uro_net_side_area_left_units xml_buffer, uro_ifc_boundary_surface_attribute{}.uro_ifc_wall_standard_case_uro_gross_side_area_right xml_real64, uro_ifc_boundary_surface_attribute{}.uro_ifc_wall_standard_case_uro_gross_side_area_right_units xml_buffer, uro_ifc_boundary_surface_attribute{}.uro_ifc_wall_standard_case_uro_net_side_area_right xml_real64, uro_ifc_boundary_surface_attribute{}.uro_ifc_wall_standard_case_uro_net_side_area_right_units xml_buffer, uro_ifc_boundary_surface_attribute{}.uro_ifc_wall_standard_case_uro_gross_volume xml_real64, uro_ifc_boundary_surface_attribute{}.uro_ifc_wall_standard_case_uro_gross_volume_units xml_buffer, uro_ifc_boundary_surface_attribute{}.uro_ifc_wall_standard_case_uro_net_volume xml_real64, uro_ifc_boundary_surface_attribute{}.uro_ifc_wall_standard_case_uro_net_volume_units xml_buffer, uro_ifc_boundary_surface_attribute{}.uro_ifc_window_uro_global_id xml_buffer, uro_ifc_boundary_surface_attribute{}.uro_ifc_window_uro_name xml_buffer, uro_ifc_boundary_surface_attribute{}.uro_ifc_window_uro_description xml_buffer, uro_ifc_boundary_surface_attribute{}.uro_ifc_window_uro_object_type xml_buffer, uro_ifc_boundary_surface_attribute{}.uro_ifc_window_uro_tag xml_buffer, uro_ifc_boundary_surface_attribute{}.uro_ifc_window_uro_element_type xml_buffer, uro_ifc_boundary_surface_attribute{}.uro_ifc_window_uro_element_type_codeSpace xml_buffer, uro_ifc_boundary_surface_attribute{}.uro_ifc_window_uro_predefined_type xml_buffer, uro_ifc_boundary_surface_attribute{}.uro_ifc_window_uro_predefined_type_codeSpace xml_buffer, uro_ifc_boundary_surface_attribute{}.uro_ifc_window_uro_shape_type xml_buffer, uro_ifc_boundary_surface_attribute{}.uro_ifc_window_uro_shape_type_codeSpace xml_buffer, uro_ifc_boundary_surface_attribute{}.uro_ifc_window_uro_number_of_riser xml_int64,
      uro_ifc_boundary_surface_attribute{}.uro_ifc_window_uro_number_of_treads xml_int64, uro_ifc_boundary_surface_attribute{}.uro_ifc_window_uro_riser_height xml_int64, uro_ifc_boundary_surface_attribute{}.uro_ifc_window_uro_tread_length xml_int64, uro_ifc_boundary_surface_attribute{}.uro_ifc_window_uro_operation_type xml_char(11), uro_ifc_boundary_surface_attribute{}.uro_ifc_window_uro_capacity_by_weight xml_real64, uro_ifc_boundary_surface_attribute{}.uro_ifc_window_uro_capacity_by_weight_units xml_buffer, uro_ifc_boundary_surface_attribute{}.uro_ifc_window_uro_capacity_by_number xml_int64, uro_ifc_boundary_surface_attribute{}.uro_ifc_window_uro_overall_height xml_real64, uro_ifc_boundary_surface_attribute{}.uro_ifc_window_uro_overall_height_units xml_buffer, uro_ifc_boundary_surface_attribute{}.uro_ifc_window_uro_overall_width xml_real64, uro_ifc_boundary_surface_attribute{}.uro_ifc_window_uro_overall_width_units xml_buffer
GroundSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, uro_ifc_boundary_surface_attribute{}.uro_ifc_building_uro_global_id xml_buffer, uro_ifc_boundary_surface_attribute{}.uro_ifc_building_uro_name xml_buffer, uro_ifc_boundary_surface_attribute{}.uro_ifc_building_uro_description xml_buffer, uro_ifc_boundary_surface_attribute{}.uro_ifc_building_uro_object_type xml_buffer, uro_ifc_boundary_surface_attribute{}.uro_ifc_building_uro_long_name xml_buffer, uro_ifc_boundary_surface_attribute{}.uro_ifc_building_uro_composition_type xml_char(7), uro_ifc_boundary_surface_attribute{}.uro_ifc_building_uro_elevation_of_ref_height xml_real64, uro_ifc_boundary_surface_attribute{}.uro_ifc_building_uro_elevation_of_ref_height_units xml_buffer, uro_ifc_boundary_surface_attribute{}.uro_ifc_building_uro_elevation_of_terrain xml_real64, uro_ifc_boundary_surface_attribute{}.uro_ifc_building_uro_elevation_of_terrain_units xml_buffer, uro_ifc_boundary_surface_attribute{}.uro_ifc_building_uro_building_address_xlink_href xml_buffer, uro_ifc_boundary_surface_attribute{}.uro_ifc_building_element_uro_global_id xml_buffer, uro_ifc_boundary_surface_attribute{}.uro_ifc_building_element_uro_name xml_buffer, uro_ifc_boundary_surface_attribute{}.uro_ifc_building_element_uro_description xml_buffer,
      uro_ifc_boundary_surface_attribute{}.uro_ifc_building_element_uro_object_type xml_buffer, uro_ifc_boundary_surface_attribute{}.uro_ifc_building_element_uro_tag xml_buffer, uro_ifc_boundary_surface_attribute{}.uro_ifc_building_element_uro_element_type xml_buffer, uro_ifc_boundary_surface_attribute{}.uro_ifc_building_element_uro_element_type_codeSpace xml_buffer, uro_ifc_boundary_surface_attribute{}.uro_ifc_building_element_uro_predefined_type xml_buffer, uro_ifc_boundary_surface_attribute{}.uro_ifc_building_element_uro_predefined_type_codeSpace xml_buffer, uro_ifc_boundary_surface_attribute{}.uro_ifc_building_element_uro_shape_type xml_buffer, uro_ifc_boundary_surface_attribute{}.uro_ifc_building_element_uro_shape_type_codeSpace xml_buffer, uro_ifc_boundary_surface_attribute{}.uro_ifc_building_element_uro_number_of_riser xml_int64, uro_ifc_boundary_surface_attribute{}.uro_ifc_building_element_uro_number_of_treads xml_int64, uro_ifc_boundary_surface_attribute{}.uro_ifc_building_element_uro_riser_height xml_int64, uro_ifc_boundary_surface_attribute{}.uro_ifc_building_element_uro_tread_length xml_int64, uro_ifc_boundary_surface_attribute{}.uro_ifc_building_element_uro_operation_type xml_char(11), uro_ifc_boundary_surface_attribute{}.uro_ifc_building_element_uro_capacity_by_weight xml_real64, uro_ifc_boundary_surface_attribute{}.uro_ifc_building_element_uro_capacity_by_weight_units xml_buffer, uro_ifc_boundary_surface_attribute{}.uro_ifc_building_element_uro_capacity_by_number xml_int64, uro_ifc_boundary_surface_attribute{}.uro_ifc_building_storey_uro_global_id xml_buffer, uro_ifc_boundary_surface_attribute{}.uro_ifc_building_storey_uro_name xml_buffer, uro_ifc_boundary_surface_attribute{}.uro_ifc_building_storey_uro_description xml_buffer, uro_ifc_boundary_surface_attribute{}.uro_ifc_building_storey_uro_object_type xml_buffer, uro_ifc_boundary_surface_attribute{}.uro_ifc_building_storey_uro_long_name xml_buffer, uro_ifc_boundary_surface_attribute{}.uro_ifc_building_storey_uro_composition_type xml_char(7), uro_ifc_boundary_surface_attribute{}.uro_ifc_building_storey_uro_elevation xml_real64, uro_ifc_boundary_surface_attribute{}.uro_ifc_building_storey_uro_elevation_units xml_buffer, uro_ifc_boundary_surface_attribute{}.uro_ifc_classification_reference_uro_location xml_buffer, uro_ifc_boundary_surface_attribute{}.uro_ifc_classification_reference_uro_item_reference xml_buffer, uro_ifc_boundary_surface_attribute{}.uro_ifc_classification_reference_uro_item_reference_codeSpace xml_buffer, uro_ifc_boundary_surface_attribute{}.uro_ifc_classification_reference_uro_name xml_buffer, uro_ifc_boundary_surface_attribute{}.uro_ifc_classification_reference_uro_name_codeSpace xml_buffer, uro_ifc_boundary_surface_attribute{}.uro_ifc_classification_reference_uro_reference_source_uro_ifc_classification_uro_source xml_buffer,
      uro_ifc_boundary_surface_attribute{}.uro_ifc_classification_reference_uro_reference_source_uro_ifc_classification_uro_edition xml_buffer, uro_ifc_boundary_surface_attribute{}.uro_ifc_classification_reference_uro_reference_source_uro_ifc_classification_uro_edition_date xml_date, uro_ifc_boundary_surface_attribute{}.uro_ifc_classification_reference_uro_reference_source_uro_ifc_classification_uro_name xml_buffer, uro_ifc_boundary_surface_attribute{}.uro_ifc_coordinate_reference_system_uro_name xml_buffer, uro_ifc_boundary_surface_attribute{}.uro_ifc_coordinate_reference_system_uro_description xml_buffer, uro_ifc_boundary_surface_attribute{}.uro_ifc_coordinate_reference_system_uro_geodetic_datum xml_buffer, uro_ifc_boundary_surface_attribute{}.uro_ifc_coordinate_reference_system_uro_vertical_datum xml_buffer, uro_ifc_boundary_surface_attribute{}.uro_ifc_curtain_wall_uro_global_id xml_buffer, uro_ifc_boundary_surface_attribute{}.uro_ifc_curtain_wall_uro_name xml_buffer, uro_ifc_boundary_surface_attribute{}.uro_ifc_curtain_wall_uro_description xml_buffer, uro_ifc_boundary_surface_attribute{}.uro_ifc_curtain_wall_uro_object_type xml_buffer, uro_ifc_boundary_surface_attribute{}.uro_ifc_curtain_wall_uro_tag xml_buffer, uro_ifc_boundary_surface_attribute{}.uro_ifc_curtain_wall_uro_element_type xml_buffer, uro_ifc_boundary_surface_attribute{}.uro_ifc_curtain_wall_uro_element_type_codeSpace xml_buffer, uro_ifc_boundary_surface_attribute{}.uro_ifc_curtain_wall_uro_predefined_type xml_buffer, uro_ifc_boundary_surface_attribute{}.uro_ifc_curtain_wall_uro_predefined_type_codeSpace xml_buffer, uro_ifc_boundary_surface_attribute{}.uro_ifc_curtain_wall_uro_shape_type xml_buffer, uro_ifc_boundary_surface_attribute{}.uro_ifc_curtain_wall_uro_shape_type_codeSpace xml_buffer, uro_ifc_boundary_surface_attribute{}.uro_ifc_curtain_wall_uro_number_of_riser xml_int64, uro_ifc_boundary_surface_attribute{}.uro_ifc_curtain_wall_uro_number_of_treads xml_int64, uro_ifc_boundary_surface_attribute{}.uro_ifc_curtain_wall_uro_riser_height xml_int64, uro_ifc_boundary_surface_attribute{}.uro_ifc_curtain_wall_uro_tread_length xml_int64, uro_ifc_boundary_surface_attribute{}.uro_ifc_curtain_wall_uro_operation_type xml_char(11), uro_ifc_boundary_surface_attribute{}.uro_ifc_curtain_wall_uro_capacity_by_weight xml_real64, uro_ifc_boundary_surface_attribute{}.uro_ifc_curtain_wall_uro_capacity_by_weight_units xml_buffer, uro_ifc_boundary_surface_attribute{}.uro_ifc_curtain_wall_uro_capacity_by_number xml_int64, uro_ifc_boundary_surface_attribute{}.uro_ifc_door_uro_global_id xml_buffer, uro_ifc_boundary_surface_attribute{}.uro_ifc_door_uro_name xml_buffer, uro_ifc_boundary_surface_attribute{}.uro_ifc_door_uro_description xml_buffer, uro_ifc_boundary_surface_attribute{}.uro_ifc_door_uro_object_type xml_buffer,
      uro_ifc_boundary_surface_attribute{}.uro_ifc_door_uro_tag xml_buffer, uro_ifc_boundary_surface_attribute{}.uro_ifc_door_uro_element_type xml_buffer, uro_ifc_boundary_surface_attribute{}.uro_ifc_door_uro_element_type_codeSpace xml_buffer, uro_ifc_boundary_surface_attribute{}.uro_ifc_door_uro_predefined_type xml_buffer, uro_ifc_boundary_surface_attribute{}.uro_ifc_door_uro_predefined_type_codeSpace xml_buffer, uro_ifc_boundary_surface_attribute{}.uro_ifc_door_uro_shape_type xml_buffer, uro_ifc_boundary_surface_attribute{}.uro_ifc_door_uro_shape_type_codeSpace xml_buffer, uro_ifc_boundary_surface_attribute{}.uro_ifc_door_uro_number_of_riser xml_int64, uro_ifc_boundary_surface_attribute{}.uro_ifc_door_uro_number_of_treads xml_int64, uro_ifc_boundary_surface_attribute{}.uro_ifc_door_uro_riser_height xml_int64, uro_ifc_boundary_surface_attribute{}.uro_ifc_door_uro_tread_length xml_int64, uro_ifc_boundary_surface_attribute{}.uro_ifc_door_uro_operation_type xml_char(11), uro_ifc_boundary_surface_attribute{}.uro_ifc_door_uro_capacity_by_weight xml_real64, uro_ifc_boundary_surface_attribute{}.uro_ifc_door_uro_capacity_by_weight_units xml_buffer, uro_ifc_boundary_surface_attribute{}.uro_ifc_door_uro_capacity_by_number xml_int64, uro_ifc_boundary_surface_attribute{}.uro_ifc_door_uro_overall_height xml_real64, uro_ifc_boundary_surface_attribute{}.uro_ifc_door_uro_overall_height_units xml_buffer, uro_ifc_boundary_surface_attribute{}.uro_ifc_door_uro_overall_width xml_real64, uro_ifc_boundary_surface_attribute{}.uro_ifc_door_uro_overall_width_units xml_buffer, uro_ifc_boundary_surface_attribute{}.uro_ifc_furnishing_element_uro_global_id xml_buffer, uro_ifc_boundary_surface_attribute{}.uro_ifc_furnishing_element_uro_name xml_buffer, uro_ifc_boundary_surface_attribute{}.uro_ifc_furnishing_element_uro_description xml_buffer, uro_ifc_boundary_surface_attribute{}.uro_ifc_furnishing_element_uro_object_type xml_buffer, uro_ifc_boundary_surface_attribute{}.uro_ifc_furnishing_element_uro_tag xml_buffer, uro_ifc_boundary_surface_attribute{}.uro_ifc_map_conversion_uro_source_crs_uro_crs_uro_ifc_projected_crs_uro_name xml_buffer, uro_ifc_boundary_surface_attribute{}.uro_ifc_map_conversion_uro_source_crs_uro_crs_uro_ifc_projected_crs_uro_description xml_buffer, uro_ifc_boundary_surface_attribute{}.uro_ifc_map_conversion_uro_source_crs_uro_crs_uro_ifc_projected_crs_uro_geodetic_datum xml_buffer, uro_ifc_boundary_surface_attribute{}.uro_ifc_map_conversion_uro_source_crs_uro_crs_uro_ifc_projected_crs_uro_vertical_datum xml_buffer, uro_ifc_boundary_surface_attribute{}.uro_ifc_map_conversion_uro_source_crs_uro_crs_uro_ifc_projected_crs_uro_map_unit xml_buffer, uro_ifc_boundary_surface_attribute{}.uro_ifc_map_conversion_uro_source_crs_uro_crs_uro_ifc_projected_crs_uro_map_projection xml_buffer,
      uro_ifc_boundary_surface_attribute{}.uro_ifc_map_conversion_uro_source_crs_uro_crs_uro_ifc_projected_crs_uro_map_zone xml_buffer, uro_ifc_boundary_surface_attribute{}.uro_ifc_map_conversion_uro_source_crs_uro_crs_uro_ifc_coordinate_reference_system_uro_name xml_buffer, uro_ifc_boundary_surface_attribute{}.uro_ifc_map_conversion_uro_source_crs_uro_crs_uro_ifc_coordinate_reference_system_uro_description xml_buffer, uro_ifc_boundary_surface_attribute{}.uro_ifc_map_conversion_uro_source_crs_uro_crs_uro_ifc_coordinate_reference_system_uro_geodetic_datum xml_buffer, uro_ifc_boundary_surface_attribute{}.uro_ifc_map_conversion_uro_source_crs_uro_crs_uro_ifc_coordinate_reference_system_uro_vertical_datum xml_buffer, uro_ifc_boundary_surface_attribute{}.uro_ifc_map_conversion_uro_source_crs_uro_context_uro_ifc_geometric_representation_context_uro_context_identifier xml_buffer, uro_ifc_boundary_surface_attribute{}.uro_ifc_map_conversion_uro_source_crs_uro_context_uro_ifc_geometric_representation_context_uro_context_type xml_buffer, uro_ifc_boundary_surface_attribute{}.uro_ifc_map_conversion_uro_source_crs_uro_context_uro_ifc_geometric_representation_context_uro_coordinate_space_dimension xml_int64, uro_ifc_boundary_surface_attribute{}.uro_ifc_map_conversion_uro_source_crs_uro_context_uro_ifc_geometric_representation_context_uro_precision xml_real64, uro_ifc_boundary_surface_attribute{}.uro_ifc_map_conversion_uro_source_crs_uro_context_uro_ifc_geometric_representation_context_uro_true_north xml_real64, uro_ifc_boundary_surface_attribute{}.uro_ifc_map_conversion_uro_target_crs_uro_ifc_projected_crs_uro_name xml_buffer, uro_ifc_boundary_surface_attribute{}.uro_ifc_map_conversion_uro_target_crs_uro_ifc_projected_crs_uro_description xml_buffer, uro_ifc_boundary_surface_attribute{}.uro_ifc_map_conversion_uro_target_crs_uro_ifc_projected_crs_uro_geodetic_datum xml_buffer, uro_ifc_boundary_surface_attribute{}.uro_ifc_map_conversion_uro_target_crs_uro_ifc_projected_crs_uro_vertical_datum xml_buffer, uro_ifc_boundary_surface_attribute{}.uro_ifc_map_conversion_uro_target_crs_uro_ifc_projected_crs_uro_map_unit xml_buffer, uro_ifc_boundary_surface_attribute{}.uro_ifc_map_conversion_uro_target_crs_uro_ifc_projected_crs_uro_map_projection xml_buffer, uro_ifc_boundary_surface_attribute{}.uro_ifc_map_conversion_uro_target_crs_uro_ifc_projected_crs_uro_map_zone xml_buffer, uro_ifc_boundary_surface_attribute{}.uro_ifc_map_conversion_uro_target_crs_uro_ifc_coordinate_reference_system_uro_name xml_buffer, uro_ifc_boundary_surface_attribute{}.uro_ifc_map_conversion_uro_target_crs_uro_ifc_coordinate_reference_system_uro_description xml_buffer, uro_ifc_boundary_surface_attribute{}.uro_ifc_map_conversion_uro_target_crs_uro_ifc_coordinate_reference_system_uro_geodetic_datum xml_buffer, uro_ifc_boundary_surface_attribute{}.uro_ifc_map_conversion_uro_target_crs_uro_ifc_coordinate_reference_system_uro_vertical_datum xml_buffer, uro_ifc_boundary_surface_attribute{}.uro_ifc_map_conversion_uro_eastings xml_buffer, uro_ifc_boundary_surface_attribute{}.uro_ifc_map_conversion_uro_northings xml_buffer, uro_ifc_boundary_surface_attribute{}.uro_ifc_map_conversion_uro_orthogonal_height xml_real64, uro_ifc_boundary_surface_attribute{}.uro_ifc_map_conversion_uro_orthogonal_height_units xml_buffer, uro_ifc_boundary_surface_attribute{}.uro_ifc_map_conversion_uro_x_axis_abscissa xml_real64, uro_ifc_boundary_surface_attribute{}.uro_ifc_map_conversion_uro_x_axis_ordinate xml_real64, uro_ifc_boundary_surface_attribute{}.uro_ifc_map_conversion_uro_scale xml_real64, uro_ifc_boundary_surface_attribute{}.uro_ifc_opening_element_uro_global_id xml_buffer, uro_ifc_boundary_surface_attribute{}.uro_ifc_opening_element_uro_name xml_buffer,
      uro_ifc_boundary_surface_attribute{}.uro_ifc_opening_element_uro_description xml_buffer, uro_ifc_boundary_surface_attribute{}.uro_ifc_opening_element_uro_object_type xml_buffer, uro_ifc_boundary_surface_attribute{}.uro_ifc_opening_element_uro_tag xml_buffer, uro_ifc_boundary_surface_attribute{}.uro_ifc_opening_element_uro_nominal_area xml_real64, uro_ifc_boundary_surface_attribute{}.uro_ifc_opening_element_uro_nominal_area_units xml_buffer, uro_ifc_boundary_surface_attribute{}.uro_ifc_opening_element_uro_nominal_volume xml_real64, uro_ifc_boundary_surface_attribute{}.uro_ifc_opening_element_uro_nominal_volume_units xml_buffer, uro_ifc_boundary_surface_attribute{}.uro_ifc_project_uro_global_id xml_buffer, uro_ifc_boundary_surface_attribute{}.uro_ifc_project_uro_name xml_buffer, uro_ifc_boundary_surface_attribute{}.uro_ifc_project_uro_description xml_buffer, uro_ifc_boundary_surface_attribute{}.uro_ifc_project_uro_object_type xml_buffer, uro_ifc_boundary_surface_attribute{}.uro_ifc_project_uro_long_name xml_buffer, uro_ifc_boundary_surface_attribute{}.uro_ifc_project_uro_phase xml_buffer, uro_ifc_boundary_surface_attribute{}.uro_ifc_project_uro_representation_contexts_uro_ifc_geometric_representation_context_uro_context_identifier xml_buffer, uro_ifc_boundary_surface_attribute{}.uro_ifc_project_uro_representation_contexts_uro_ifc_geometric_representation_context_uro_context_type xml_buffer, uro_ifc_boundary_surface_attribute{}.uro_ifc_project_uro_representation_contexts_uro_ifc_geometric_representation_context_uro_coordinate_space_dimension xml_int64, uro_ifc_boundary_surface_attribute{}.uro_ifc_project_uro_representation_contexts_uro_ifc_geometric_representation_context_uro_precision xml_real64, uro_ifc_boundary_surface_attribute{}.uro_ifc_project_uro_representation_contexts_uro_ifc_geometric_representation_context_uro_true_north xml_real64, uro_ifc_boundary_surface_attribute{}.uro_ifc_project_uro_units_in_context{}.uro_ifc_unit_uro_dimensions xml_int64, uro_ifc_boundary_surface_attribute{}.uro_ifc_project_uro_units_in_context{}.uro_ifc_unit_uro_unit_type xml_char(28), uro_ifc_boundary_surface_attribute{}.uro_ifc_project_uro_units_in_context{}.uro_ifc_unit_uro_perfix xml_buffer, uro_ifc_boundary_surface_attribute{}.uro_ifc_project_uro_units_in_context{}.uro_ifc_unit_uro_name xml_buffer, uro_ifc_boundary_surface_attribute{}.uro_ifc_projected_crs_uro_name xml_buffer, uro_ifc_boundary_surface_attribute{}.uro_ifc_projected_crs_uro_description xml_buffer, uro_ifc_boundary_surface_attribute{}.uro_ifc_projected_crs_uro_geodetic_datum xml_buffer, uro_ifc_boundary_surface_attribute{}.uro_ifc_projected_crs_uro_vertical_datum xml_buffer, uro_ifc_boundary_surface_attribute{}.uro_ifc_projected_crs_uro_map_unit xml_buffer, uro_ifc_boundary_surface_attribute{}.uro_ifc_projected_crs_uro_map_projection xml_buffer, uro_ifc_boundary_surface_attribute{}.uro_ifc_projected_crs_uro_map_zone xml_buffer, uro_ifc_boundary_surface_attribute{}.uro_ifc_pset_building_common_uro_building_id xml_real64,
      uro_ifc_boundary_surface_attribute{}.uro_ifc_pset_building_common_uro_building_id_units xml_buffer, uro_ifc_boundary_surface_attribute{}.uro_ifc_pset_building_common_uro_is_permanent_id xml_real64, uro_ifc_boundary_surface_attribute{}.uro_ifc_pset_building_common_uro_is_permanent_id_units xml_buffer, uro_ifc_boundary_surface_attribute{}.uro_ifc_pset_building_common_uro_main_fire_use xml_buffer, uro_ifc_boundary_surface_attribute{}.uro_ifc_pset_building_common_uro_ancillary_fire_use xml_buffer, uro_ifc_boundary_surface_attribute{}.uro_ifc_pset_building_common_uro_sprinkler_protection xml_boolean, uro_ifc_boundary_surface_attribute{}.uro_ifc_pset_building_common_uro_sprinkler_protection_automatic xml_boolean, uro_ifc_boundary_surface_attribute{}.uro_ifc_pset_building_common_uro_occupancy_type xml_buffer, uro_ifc_boundary_surface_attribute{}.uro_ifc_pset_building_common_uro_occupancy_type_codeSpace xml_buffer, uro_ifc_boundary_surface_attribute{}.uro_ifc_pset_building_common_uro_gross_planned_area xml_real64, uro_ifc_boundary_surface_attribute{}.uro_ifc_pset_building_common_uro_gross_planned_area_units xml_buffer, uro_ifc_boundary_surface_attribute{}.uro_ifc_pset_building_common_uro_number_of_storeys xml_int64, uro_ifc_boundary_surface_attribute{}.uro_ifc_pset_building_common_uro_year_of_construction xml_buffer, uro_ifc_boundary_surface_attribute{}.uro_ifc_pset_building_common_uro_is_landmarked xml_boolean, uro_ifc_boundary_surface_attribute{}.uro_ifc_pset_door_common_uro_reference xml_buffer, uro_ifc_boundary_surface_attribute{}.uro_ifc_pset_door_common_uro_acoustic_rating xml_buffer, uro_ifc_boundary_surface_attribute{}.uro_ifc_pset_door_common_uro_firerating xml_buffer, uro_ifc_boundary_surface_attribute{}.uro_ifc_pset_door_common_uro_security_rating xml_buffer, uro_ifc_boundary_surface_attribute{}.uro_ifc_pset_door_common_uro_is_external xml_boolean, uro_ifc_boundary_surface_attribute{}.uro_ifc_pset_door_common_uro_infiltration xml_real64, uro_ifc_boundary_surface_attribute{}.uro_ifc_pset_door_common_uro_thermal_transmittance xml_real64, uro_ifc_boundary_surface_attribute{}.uro_ifc_pset_door_common_uro_glazing_area_fraction xml_real64, uro_ifc_boundary_surface_attribute{}.uro_ifc_pset_door_common_uro_handicap_accessible xml_real64, uro_ifc_boundary_surface_attribute{}.uro_ifc_pset_door_common_uro_fire_exit xml_boolean, uro_ifc_boundary_surface_attribute{}.uro_ifc_pset_door_common_uro_self_closing xml_real64, uro_ifc_boundary_surface_attribute{}.uro_ifc_pset_door_common_uro_smoke_stop xml_boolean, uro_ifc_boundary_surface_attribute{}.uro_ifc_pset_opening_element_common_uro_reference xml_buffer, uro_ifc_boundary_surface_attribute{}.uro_ifc_pset_opening_element_common_uro_purpose xml_buffer, uro_ifc_boundary_surface_attribute{}.uro_ifc_pset_opening_element_common_uro_fire_exit xml_boolean, uro_ifc_boundary_surface_attribute{}.uro_ifc_pset_opening_element_common_uro_protected_opening xml_boolean,
      uro_ifc_boundary_surface_attribute{}.uro_ifc_pset_opening_element_common_uro_parallel_jambs xml_boolean, uro_ifc_boundary_surface_attribute{}.uro_ifc_pset_site_common_uro_buildable_area xml_real64, uro_ifc_boundary_surface_attribute{}.uro_ifc_pset_site_common_uro_buildable_area_units xml_buffer, uro_ifc_boundary_surface_attribute{}.uro_ifc_pset_site_common_uro_total_area xml_real64, uro_ifc_boundary_surface_attribute{}.uro_ifc_pset_site_common_uro_total_area_units xml_buffer, uro_ifc_boundary_surface_attribute{}.uro_ifc_pset_site_common_uro_building_height_limit xml_real64, uro_ifc_boundary_surface_attribute{}.uro_ifc_pset_site_common_uro_building_height_limit_units xml_buffer, uro_ifc_boundary_surface_attribute{}.uro_ifc_pset_space_common_uro_reference xml_buffer, uro_ifc_boundary_surface_attribute{}.uro_ifc_pset_space_common_uro_category xml_buffer, uro_ifc_boundary_surface_attribute{}.uro_ifc_pset_space_common_uro_category_codeSpace xml_buffer, uro_ifc_boundary_surface_attribute{}.uro_ifc_pset_space_common_uro_floor_covering xml_buffer, uro_ifc_boundary_surface_attribute{}.uro_ifc_pset_space_common_uro_wall_covering xml_buffer, uro_ifc_boundary_surface_attribute{}.uro_ifc_pset_space_common_uro_ceiling_covering xml_buffer, uro_ifc_boundary_surface_attribute{}.uro_ifc_pset_space_common_uro_skirting_covering xml_buffer, uro_ifc_boundary_surface_attribute{}.uro_ifc_pset_space_common_uro_gross_planned_area xml_real64, uro_ifc_boundary_surface_attribute{}.uro_ifc_pset_space_common_uro_gross_planned_area_units xml_buffer, uro_ifc_boundary_surface_attribute{}.uro_ifc_pset_space_common_uro_net_planned_area xml_real64, uro_ifc_boundary_surface_attribute{}.uro_ifc_pset_space_common_uro_net_planned_area_units xml_buffer, uro_ifc_boundary_surface_attribute{}.uro_ifc_pset_space_common_uro_publicly_accessible xml_boolean, uro_ifc_boundary_surface_attribute{}.uro_ifc_pset_space_common_uro_handicap_accessible xml_boolean, uro_ifc_boundary_surface_attribute{}.uro_ifc_pset_space_common_uro_concealed_flooring xml_boolean, uro_ifc_boundary_surface_attribute{}.uro_ifc_pset_space_common_uro_concealed_ceiling xml_boolean, uro_ifc_boundary_surface_attribute{}.uro_ifc_pset_window_common_uro_reference xml_buffer, uro_ifc_boundary_surface_attribute{}.uro_ifc_pset_window_common_uro_acoustic_rating xml_buffer, uro_ifc_boundary_surface_attribute{}.uro_ifc_pset_window_common_uro_firerating xml_buffer, uro_ifc_boundary_surface_attribute{}.uro_ifc_pset_window_common_uro_security_rating xml_buffer, uro_ifc_boundary_surface_attribute{}.uro_ifc_pset_window_common_uro_is_external xml_boolean, uro_ifc_boundary_surface_attribute{}.uro_ifc_pset_window_common_uro_infiltration xml_real64, uro_ifc_boundary_surface_attribute{}.uro_ifc_pset_window_common_uro_thermal_transmittance xml_real64, uro_ifc_boundary_surface_attribute{}.uro_ifc_pset_window_common_uro_glazing_area_fraction xml_real64,
      uro_ifc_boundary_surface_attribute{}.uro_ifc_pset_window_common_uro_smoke_stop xml_boolean, uro_ifc_boundary_surface_attribute{}.uro_ifc_site_uro_global_id xml_buffer, uro_ifc_boundary_surface_attribute{}.uro_ifc_site_uro_name xml_buffer, uro_ifc_boundary_surface_attribute{}.uro_ifc_site_uro_description xml_buffer, uro_ifc_boundary_surface_attribute{}.uro_ifc_site_uro_object_type xml_buffer, uro_ifc_boundary_surface_attribute{}.uro_ifc_site_uro_long_name xml_buffer, uro_ifc_boundary_surface_attribute{}.uro_ifc_site_uro_composition_type xml_char(7), uro_ifc_boundary_surface_attribute{}.uro_ifc_site_uro_ref_longitude xml_real64, uro_ifc_boundary_surface_attribute{}.uro_ifc_site_uro_ref_latitude xml_real64, uro_ifc_boundary_surface_attribute{}.uro_ifc_site_uro_ref_elevation xml_real64, uro_ifc_boundary_surface_attribute{}.uro_ifc_site_uro_ref_elevation_units xml_buffer, uro_ifc_boundary_surface_attribute{}.uro_ifc_site_uro_land_title_number xml_buffer, uro_ifc_boundary_surface_attribute{}.uro_ifc_site_uro_site_address_xlink_href xml_buffer, uro_ifc_boundary_surface_attribute{}.uro_ifc_space_uro_global_id xml_buffer, uro_ifc_boundary_surface_attribute{}.uro_ifc_space_uro_name xml_buffer, uro_ifc_boundary_surface_attribute{}.uro_ifc_space_uro_description xml_buffer, uro_ifc_boundary_surface_attribute{}.uro_ifc_space_uro_object_type xml_buffer, uro_ifc_boundary_surface_attribute{}.uro_ifc_space_uro_long_name xml_buffer, uro_ifc_boundary_surface_attribute{}.uro_ifc_space_uro_composition_type xml_char(7), uro_ifc_boundary_surface_attribute{}.uro_ifc_space_uro_interioror_exterior_space xml_char(10), uro_ifc_boundary_surface_attribute{}.uro_ifc_space_uro_elevation_with_flooring xml_real64, uro_ifc_boundary_surface_attribute{}.uro_ifc_space_uro_elevation_with_flooring_units xml_buffer, uro_ifc_boundary_surface_attribute{}.uro_ifc_space_base_quantity_uro_nominal_height xml_real64, uro_ifc_boundary_surface_attribute{}.uro_ifc_space_base_quantity_uro_nominal_height_units xml_buffer, uro_ifc_boundary_surface_attribute{}.uro_ifc_space_base_quantity_uro_clear_height xml_real64, uro_ifc_boundary_surface_attribute{}.uro_ifc_space_base_quantity_uro_clear_height_units xml_buffer, uro_ifc_boundary_surface_attribute{}.uro_ifc_space_base_quantity_uro_finish_ceiling_height xml_real64, uro_ifc_boundary_surface_attribute{}.uro_ifc_space_base_quantity_uro_finish_ceiling_height_units xml_buffer, uro_ifc_boundary_surface_attribute{}.uro_ifc_space_base_quantity_uro_gross_perimeter xml_real64, uro_ifc_boundary_surface_attribute{}.uro_ifc_space_base_quantity_uro_gross_perimeter_units xml_buffer,
      uro_ifc_boundary_surface_attribute{}.uro_ifc_space_base_quantity_uro_net_perimeter xml_real64, uro_ifc_boundary_surface_attribute{}.uro_ifc_space_base_quantity_uro_net_perimeter_units xml_buffer, uro_ifc_boundary_surface_attribute{}.uro_ifc_space_base_quantity_uro_gross_ceiling_area xml_real64, uro_ifc_boundary_surface_attribute{}.uro_ifc_space_base_quantity_uro_gross_ceiling_area_units xml_buffer, uro_ifc_boundary_surface_attribute{}.uro_ifc_space_base_quantity_uro_gross_floor_area xml_real64, uro_ifc_boundary_surface_attribute{}.uro_ifc_space_base_quantity_uro_gross_floor_area_units xml_buffer, uro_ifc_boundary_surface_attribute{}.uro_ifc_space_base_quantity_uro_net_ceiling_area xml_real64, uro_ifc_boundary_surface_attribute{}.uro_ifc_space_base_quantity_uro_net_ceiling_area_units xml_buffer, uro_ifc_boundary_surface_attribute{}.uro_ifc_space_base_quantity_uro_net_floor_area xml_real64, uro_ifc_boundary_surface_attribute{}.uro_ifc_space_base_quantity_uro_net_floor_area_units xml_buffer, uro_ifc_boundary_surface_attribute{}.uro_ifc_space_base_quantity_uro_gross_wall_area xml_real64, uro_ifc_boundary_surface_attribute{}.uro_ifc_space_base_quantity_uro_gross_wall_area_units xml_buffer, uro_ifc_boundary_surface_attribute{}.uro_ifc_space_base_quantity_uro_net_wall_area xml_real64, uro_ifc_boundary_surface_attribute{}.uro_ifc_space_base_quantity_uro_net_wall_area_units xml_buffer, uro_ifc_boundary_surface_attribute{}.uro_ifc_space_base_quantity_uro_gross_volume xml_real64, uro_ifc_boundary_surface_attribute{}.uro_ifc_space_base_quantity_uro_gross_volume_units xml_buffer, uro_ifc_boundary_surface_attribute{}.uro_ifc_space_base_quantity_uro_net_volume xml_real64, uro_ifc_boundary_surface_attribute{}.uro_ifc_space_base_quantity_uro_net_volume_units xml_buffer, uro_ifc_boundary_surface_attribute{}.uro_ifc_wall_uro_global_id xml_buffer, uro_ifc_boundary_surface_attribute{}.uro_ifc_wall_uro_name xml_buffer, uro_ifc_boundary_surface_attribute{}.uro_ifc_wall_uro_description xml_buffer, uro_ifc_boundary_surface_attribute{}.uro_ifc_wall_uro_object_type xml_buffer, uro_ifc_boundary_surface_attribute{}.uro_ifc_wall_uro_tag xml_buffer, uro_ifc_boundary_surface_attribute{}.uro_ifc_wall_uro_element_type xml_buffer, uro_ifc_boundary_surface_attribute{}.uro_ifc_wall_uro_element_type_codeSpace xml_buffer, uro_ifc_boundary_surface_attribute{}.uro_ifc_wall_uro_predefined_type xml_buffer, uro_ifc_boundary_surface_attribute{}.uro_ifc_wall_uro_predefined_type_codeSpace xml_buffer, uro_ifc_boundary_surface_attribute{}.uro_ifc_wall_uro_shape_type xml_buffer, uro_ifc_boundary_surface_attribute{}.uro_ifc_wall_uro_shape_type_codeSpace xml_buffer, uro_ifc_boundary_surface_attribute{}.uro_ifc_wall_uro_number_of_riser xml_int64,
      uro_ifc_boundary_surface_attribute{}.uro_ifc_wall_uro_number_of_treads xml_int64, uro_ifc_boundary_surface_attribute{}.uro_ifc_wall_uro_riser_height xml_int64, uro_ifc_boundary_surface_attribute{}.uro_ifc_wall_uro_tread_length xml_int64, uro_ifc_boundary_surface_attribute{}.uro_ifc_wall_uro_operation_type xml_char(11), uro_ifc_boundary_surface_attribute{}.uro_ifc_wall_uro_capacity_by_weight xml_real64, uro_ifc_boundary_surface_attribute{}.uro_ifc_wall_uro_capacity_by_weight_units xml_buffer, uro_ifc_boundary_surface_attribute{}.uro_ifc_wall_uro_capacity_by_number xml_int64, uro_ifc_boundary_surface_attribute{}.uro_ifc_wall_uro_nominal_length xml_real64, uro_ifc_boundary_surface_attribute{}.uro_ifc_wall_uro_nominal_length_units xml_buffer, uro_ifc_boundary_surface_attribute{}.uro_ifc_wall_uro_nominal_width xml_real64, uro_ifc_boundary_surface_attribute{}.uro_ifc_wall_uro_nominal_width_units xml_buffer, uro_ifc_boundary_surface_attribute{}.uro_ifc_wall_uro_nominal_height xml_real64, uro_ifc_boundary_surface_attribute{}.uro_ifc_wall_uro_nominal_height_units xml_buffer, uro_ifc_boundary_surface_attribute{}.uro_ifc_wall_uro_gross_foot_print_area xml_real64, uro_ifc_boundary_surface_attribute{}.uro_ifc_wall_uro_gross_foot_print_area_units xml_buffer, uro_ifc_boundary_surface_attribute{}.uro_ifc_wall_uro_net_foot_print_area xml_real64, uro_ifc_boundary_surface_attribute{}.uro_ifc_wall_uro_net_foot_print_area_units xml_buffer, uro_ifc_boundary_surface_attribute{}.uro_ifc_wall_uro_gross_side_area xml_real64, uro_ifc_boundary_surface_attribute{}.uro_ifc_wall_uro_gross_side_area_units xml_buffer, uro_ifc_boundary_surface_attribute{}.uro_ifc_wall_uro_net_side_area xml_real64, uro_ifc_boundary_surface_attribute{}.uro_ifc_wall_uro_net_side_area_units xml_buffer, uro_ifc_boundary_surface_attribute{}.uro_ifc_wall_uro_gross_side_area_left xml_real64, uro_ifc_boundary_surface_attribute{}.uro_ifc_wall_uro_gross_side_area_left_units xml_buffer, uro_ifc_boundary_surface_attribute{}.uro_ifc_wall_uro_net_side_area_left xml_real64, uro_ifc_boundary_surface_attribute{}.uro_ifc_wall_uro_net_side_area_left_units xml_buffer, uro_ifc_boundary_surface_attribute{}.uro_ifc_wall_uro_gross_side_area_right xml_real64, uro_ifc_boundary_surface_attribute{}.uro_ifc_wall_uro_gross_side_area_right_units xml_buffer, uro_ifc_boundary_surface_attribute{}.uro_ifc_wall_uro_net_side_area_right xml_real64, uro_ifc_boundary_surface_attribute{}.uro_ifc_wall_uro_net_side_area_right_units xml_buffer, uro_ifc_boundary_surface_attribute{}.uro_ifc_wall_uro_gross_volume xml_real64,
      uro_ifc_boundary_surface_attribute{}.uro_ifc_wall_uro_gross_volume_units xml_buffer, uro_ifc_boundary_surface_attribute{}.uro_ifc_wall_uro_net_volume xml_real64, uro_ifc_boundary_surface_attribute{}.uro_ifc_wall_uro_net_volume_units xml_buffer, uro_ifc_boundary_surface_attribute{}.uro_ifc_wall_standard_case_uro_global_id xml_buffer, uro_ifc_boundary_surface_attribute{}.uro_ifc_wall_standard_case_uro_name xml_buffer, uro_ifc_boundary_surface_attribute{}.uro_ifc_wall_standard_case_uro_description xml_buffer, uro_ifc_boundary_surface_attribute{}.uro_ifc_wall_standard_case_uro_object_type xml_buffer, uro_ifc_boundary_surface_attribute{}.uro_ifc_wall_standard_case_uro_tag xml_buffer, uro_ifc_boundary_surface_attribute{}.uro_ifc_wall_standard_case_uro_element_type xml_buffer, uro_ifc_boundary_surface_attribute{}.uro_ifc_wall_standard_case_uro_element_type_codeSpace xml_buffer, uro_ifc_boundary_surface_attribute{}.uro_ifc_wall_standard_case_uro_predefined_type xml_buffer, uro_ifc_boundary_surface_attribute{}.uro_ifc_wall_standard_case_uro_predefined_type_codeSpace xml_buffer, uro_ifc_boundary_surface_attribute{}.uro_ifc_wall_standard_case_uro_shape_type xml_buffer, uro_ifc_boundary_surface_attribute{}.uro_ifc_wall_standard_case_uro_shape_type_codeSpace xml_buffer, uro_ifc_boundary_surface_attribute{}.uro_ifc_wall_standard_case_uro_number_of_riser xml_int64, uro_ifc_boundary_surface_attribute{}.uro_ifc_wall_standard_case_uro_number_of_treads xml_int64, uro_ifc_boundary_surface_attribute{}.uro_ifc_wall_standard_case_uro_riser_height xml_int64, uro_ifc_boundary_surface_attribute{}.uro_ifc_wall_standard_case_uro_tread_length xml_int64, uro_ifc_boundary_surface_attribute{}.uro_ifc_wall_standard_case_uro_operation_type xml_char(11), uro_ifc_boundary_surface_attribute{}.uro_ifc_wall_standard_case_uro_capacity_by_weight xml_real64, uro_ifc_boundary_surface_attribute{}.uro_ifc_wall_standard_case_uro_capacity_by_weight_units xml_buffer, uro_ifc_boundary_surface_attribute{}.uro_ifc_wall_standard_case_uro_capacity_by_number xml_int64, uro_ifc_boundary_surface_attribute{}.uro_ifc_wall_standard_case_uro_nominal_length xml_real64, uro_ifc_boundary_surface_attribute{}.uro_ifc_wall_standard_case_uro_nominal_length_units xml_buffer, uro_ifc_boundary_surface_attribute{}.uro_ifc_wall_standard_case_uro_nominal_width xml_real64, uro_ifc_boundary_surface_attribute{}.uro_ifc_wall_standard_case_uro_nominal_width_units xml_buffer, uro_ifc_boundary_surface_attribute{}.uro_ifc_wall_standard_case_uro_nominal_height xml_real64, uro_ifc_boundary_surface_attribute{}.uro_ifc_wall_standard_case_uro_nominal_height_units xml_buffer, uro_ifc_boundary_surface_attribute{}.uro_ifc_wall_standard_case_uro_gross_foot_print_area xml_real64, uro_ifc_boundary_surface_attribute{}.uro_ifc_wall_standard_case_uro_gross_foot_print_area_units xml_buffer,
      uro_ifc_boundary_surface_attribute{}.uro_ifc_wall_standard_case_uro_net_foot_print_area xml_real64, uro_ifc_boundary_surface_attribute{}.uro_ifc_wall_standard_case_uro_net_foot_print_area_units xml_buffer, uro_ifc_boundary_surface_attribute{}.uro_ifc_wall_standard_case_uro_gross_side_area xml_real64, uro_ifc_boundary_surface_attribute{}.uro_ifc_wall_standard_case_uro_gross_side_area_units xml_buffer, uro_ifc_boundary_surface_attribute{}.uro_ifc_wall_standard_case_uro_net_side_area xml_real64, uro_ifc_boundary_surface_attribute{}.uro_ifc_wall_standard_case_uro_net_side_area_units xml_buffer, uro_ifc_boundary_surface_attribute{}.uro_ifc_wall_standard_case_uro_gross_side_area_left xml_real64, uro_ifc_boundary_surface_attribute{}.uro_ifc_wall_standard_case_uro_gross_side_area_left_units xml_buffer, uro_ifc_boundary_surface_attribute{}.uro_ifc_wall_standard_case_uro_net_side_area_left xml_real64, uro_ifc_boundary_surface_attribute{}.uro_ifc_wall_standard_case_uro_net_side_area_left_units xml_buffer, uro_ifc_boundary_surface_attribute{}.uro_ifc_wall_standard_case_uro_gross_side_area_right xml_real64, uro_ifc_boundary_surface_attribute{}.uro_ifc_wall_standard_case_uro_gross_side_area_right_units xml_buffer, uro_ifc_boundary_surface_attribute{}.uro_ifc_wall_standard_case_uro_net_side_area_right xml_real64, uro_ifc_boundary_surface_attribute{}.uro_ifc_wall_standard_case_uro_net_side_area_right_units xml_buffer, uro_ifc_boundary_surface_attribute{}.uro_ifc_wall_standard_case_uro_gross_volume xml_real64, uro_ifc_boundary_surface_attribute{}.uro_ifc_wall_standard_case_uro_gross_volume_units xml_buffer, uro_ifc_boundary_surface_attribute{}.uro_ifc_wall_standard_case_uro_net_volume xml_real64, uro_ifc_boundary_surface_attribute{}.uro_ifc_wall_standard_case_uro_net_volume_units xml_buffer, uro_ifc_boundary_surface_attribute{}.uro_ifc_window_uro_global_id xml_buffer, uro_ifc_boundary_surface_attribute{}.uro_ifc_window_uro_name xml_buffer, uro_ifc_boundary_surface_attribute{}.uro_ifc_window_uro_description xml_buffer, uro_ifc_boundary_surface_attribute{}.uro_ifc_window_uro_object_type xml_buffer, uro_ifc_boundary_surface_attribute{}.uro_ifc_window_uro_tag xml_buffer, uro_ifc_boundary_surface_attribute{}.uro_ifc_window_uro_element_type xml_buffer, uro_ifc_boundary_surface_attribute{}.uro_ifc_window_uro_element_type_codeSpace xml_buffer, uro_ifc_boundary_surface_attribute{}.uro_ifc_window_uro_predefined_type xml_buffer, uro_ifc_boundary_surface_attribute{}.uro_ifc_window_uro_predefined_type_codeSpace xml_buffer, uro_ifc_boundary_surface_attribute{}.uro_ifc_window_uro_shape_type xml_buffer, uro_ifc_boundary_surface_attribute{}.uro_ifc_window_uro_shape_type_codeSpace xml_buffer, uro_ifc_boundary_surface_attribute{}.uro_ifc_window_uro_number_of_riser xml_int64,
      uro_ifc_boundary_surface_attribute{}.uro_ifc_window_uro_number_of_treads xml_int64, uro_ifc_boundary_surface_attribute{}.uro_ifc_window_uro_riser_height xml_int64, uro_ifc_boundary_surface_attribute{}.uro_ifc_window_uro_tread_length xml_int64, uro_ifc_boundary_surface_attribute{}.uro_ifc_window_uro_operation_type xml_char(11), uro_ifc_boundary_surface_attribute{}.uro_ifc_window_uro_capacity_by_weight xml_real64, uro_ifc_boundary_surface_attribute{}.uro_ifc_window_uro_capacity_by_weight_units xml_buffer, uro_ifc_boundary_surface_attribute{}.uro_ifc_window_uro_capacity_by_number xml_int64, uro_ifc_boundary_surface_attribute{}.uro_ifc_window_uro_overall_height xml_real64, uro_ifc_boundary_surface_attribute{}.uro_ifc_window_uro_overall_height_units xml_buffer, uro_ifc_boundary_surface_attribute{}.uro_ifc_window_uro_overall_width xml_real64, uro_ifc_boundary_surface_attribute{}.uro_ifc_window_uro_overall_width_units xml_buffer
Note: Building に集約 / AttributeManager_12 : Input
Junction_31
    -> Junction_32
Note: IfcSlab (Roof, OuterFloor, OuterCeiling, Ground) / AttributeManager_9 : Output
Junction_32
    -> AttributeManager_12
Junction_36
Note: 屋内空間と交差するものを除外
SpatialFilter
    AGGREGATE_HANDLING = Yes
    ATTR_ACCUM_MODE = Merge Filter
    ATTR_CONFLICT_RES = Use Candidate
    BASE_TYPE = Multiple Filters
    CURVE_BOUNDARY_RULE_PARAM = Default Rule
    GROUP_BY = _building_id _storey_id
    PASS_CRITERIA = Pass Against One Filter
    PREDATTR = _predicate
    PREDICATES = INTERSECTS
    USE_BOUNDING_BOX = No
    FAILED -> GeometryFilter_3
GeometryFilter_3
    FILTER_MODE = SIMPLE
    FILTER_MULTI = FILTER_TYPES]Area]FME_CONTROLLER_QUERY_FILE]]FME_CONTROLLER_CHOICE]Simple
    Area -> Counter
    <UNFILTERED> -> Junction_18
Junction_18
    -> CenterPointReplacer
    -> w4
w4: Inspector [off]
    TACKATTRS = _storey_id
Note: 中心ポイントに変換
CenterPointReplacer
    POINTTYPE = CENTER
    POINT -> NeighborFinder [BASE]
    POINT -> w5
w5: Inspector [off]
    TACKATTRS = _storey_id
Note: 屋内空間+壁の外周に近接するものを選択
NeighborFinder
    CANDIDATES_FIRST = No
    GROUP_BY = _building_id _storey_id
    INSERT_VERTEX = No
    K = 1
    MAX = 100
    MEASURES_FROM_CANDIDATE = Yes
    MEASURE_TYPE = Continuous
    MODE = Bases and Candidates
    TREAT_POLYGON_AS = Lines
    MATCHED -> GeometryReplacer
    MATCHED -> w6
Note: 元のジオメトリを復元
GeometryReplacer
    KIND_LONG = FME Binary
    REMOVE_ATTRIBUTE = Yes
    SOURCE = @Value(_geometry)
    -> SurfaceSplitter
SurfaceSplitter
    FRONT -> Clipper [CANDIDATE]
    FRONT -> w7
Note: 開口部に穴を開ける
Clipper
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    GROUP_BY = _building_id _storey_id
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Tester_2
    OUTSIDE -> Counter_3
    OUTSIDE -> w8
Tester_2
    BOOL_OP = OR
    TEST_CLAUSE = TEST @Value(_opening_ifc_feature_type) IN IfcDoor,IfcWindow
    TEST_MODE = TEST
    PASSED -> AttributeManager_25
AttributeManager_25
    ATTR_TABLE:
      REMOVE _storey_id
      REMOVE _storey_index
      REMOVE gml_description
      REMOVE gml_name
      REMOVE GlobalId
      REMOVE Name
      REMOVE ObjectType
      REMOVE LongName
      REMOVE CompositionType
      REMOVE Elevation
      REMOVE ElevationWithFlooring
      REMOVE InteriorOrExteriorSpace
      REMOVE LandTitleNumber
      REMOVE NumberOfRiser
      REMOVE NumberOfTreads
      REMOVE OverallHeight
      REMOVE OverallWidth
      REMOVE Tag
      REMOVE ifc_parent_unique_id
      REMOVE ApplicableOccurrence
      REMOVE ElementType
      REMOVE ifc_type_name
      REMOVE ifc_type_object_id
      REMOVE _lengthunit
      REMOVE _reprojection_params
      REMOVE _ifc_feature_type
      REMOVE _lengthmultiplier
      REMOVE _coordinate_precision
      REMOVE fme_feature_type
      REMOVE fme_basename
      REMOVE Description
      REMOVE _storey_name
      REMOVE _parent_feature_type
      REMOVE _geometry_name
      REMOVE _shared_item_id.front{}
      REMOVE fme_rejection_code
      REMOVE _issues{}.count
      REMOVE _issues{}.issue_found
      REMOVE _issues{}.location_sample.x
      REMOVE _issues{}.location_sample.y
      REMOVE _issues{}.location_sample.z
      REMOVE _surfaceNormalX
      REMOVE _surfaceNormalY
      REMOVE _surfaceNormalZ
      REMOVE _pointOnSurfaceX
      REMOVE _pointOnSurfaceY
      REMOVE _pointOnSurfaceZ
      REMOVE _temp_id
      REMOVE _remnant
      REMOVE _length
      REMOVE _distance
      REMOVE _angle
      REMOVE _candidate_angle
      REMOVE _candidate_label_angle
      REMOVE _closest_candidate_x
      REMOVE _closest_candidate_y
      REMOVE _closest_base_x
      REMOVE _closest_base_y
      REMOVE _clipped
    -> FeatureMerger_9 [REQUESTOR]
AttributeManager_8
    ATTR_TABLE:
      REMOVE Name
      REMOVE ifc_parent_unique_id
      REMOVE _geometry_name
      REMOVE _surfaceNormalX
      REMOVE _surfaceNormalY
      REMOVE _surfaceNormalZ
      REMOVE _pointOnSurfaceX
      REMOVE _pointOnSurfaceY
      REMOVE _pointOnSurfaceZ
      REMOVE _remnant
      REMOVE _length
      REMOVE _distance
      REMOVE _angle
      REMOVE _candidate_angle
      REMOVE _candidate_label_angle
      REMOVE _closest_candidate_x
      REMOVE _closest_candidate_y
      REMOVE _closest_base_x
      REMOVE _closest_base_y
      SET_TO gml_id = face_@UUID()
      SET_TO citygml_lod_name = lod4MultiSurface
      REMOVE _clipped
      REMOVE _temp_id
      REMOVE _issues{}.count
      REMOVE _issues{}.issue_found
      REMOVE _issues{}.location_sample.x
      REMOVE _issues{}.location_sample.y
      REMOVE _issues{}.location_sample.z
      REMOVE _parent_feature_type
      REMOVE _part_number
      REMOVE _overlaps
      REMOVE _zmin
      REMOVE _zmax
      REMOVE _zmax.max
      REMOVE _zmin.min
      REMOVE _shared_item_id.front{}
    -> AttributeManager_12
    -> GeometryPropertySetter
GeometryPropertySetter
    GQUERY:
      for $geom in //geometry
      where $geom/count(parent::geometry) = 0
      return number($geom/@fme_id)
    OVERWRITE_CHOICE = Yes
    REMOVE_ATTRIBUTE = Yes
    SETTYPE_PARAM = Traits From Attributes
    SRC_ATTRS = citygml_lod_name gml_id
    SET -> AttributeCreator_5
AttributeCreator_5
    ATTR_TABLE:
      SET_TO gml_id = bdry_@UUID()
      SET_TO gml_parent_id = @Value(_building_id)
      SET_TO citygml_feature_role = boundedBy
      SET_TO _citygml_feature_type = WallSurface
    -> GeometryFilter_5
    -> AttributeManager_2
AttributeManager_2
    ATTR_TABLE:
      REMOVE gml_parent_id
      RENAME_SET_VALUE gml_id > gml_parent_id
      REMOVE fme_feature_type
      REMOVE _storey_id
      REMOVE _storey_name
      REMOVE citygml_feature_role
      REMOVE _citygml_feature_type
      REMOVE ApplicableOccurrence
      REMOVE ElementType
      REMOVE ifc_type_name
      REMOVE ifc_type_object_id
      REMOVE _reprojection_params
      REMOVE _lengthunit
      REMOVE fme_basename
      REMOVE fme_rejection_code
      REMOVE _shared_item_id
      REMOVE gml_description
      REMOVE gml_name
      REMOVE GlobalId
      REMOVE ObjectType
      REMOVE LongName
      REMOVE CompositionType
      REMOVE Elevation
      REMOVE ElevationWithFlooring
      REMOVE InteriorOrExteriorSpace
      REMOVE LandTitleNumber
      REMOVE NumberOfRiser
      REMOVE NumberOfTreads
      REMOVE OverallHeight
      REMOVE OverallWidth
      REMOVE Tag
      REMOVE _ifc_feature_type
      REMOVE _lengthmultiplier
      REMOVE _coordinate_precision
      REMOVE Description
      REMOVE _storey_index
    USER_EXPOSED_ATTRIBUTES = gml_id,fme_feature_type,Name,ifc_parent_unique_id,ifc_unique_id,_storey_id,_storey_name,_geometry_name,_clipped,_surfaceNormalX,_surfaceNormalY,_surfaceNormalZ,_pointOnSurfaceX,_pointOnSurfaceY,_pointOnSurfaceZ,_predicate
    -> FeatureMerger_9 [SUPPLIER]
Note: 親の境界面 gml:id 結合 / gml_parent_id
FeatureMerger_9
    ATTR_ACCUM_MODE = Merge Supplier
    ATTR_CONFLICT_RES = Use Requestor
    CLEANING_TOLERANCE = Automatic
    CONNECT_Z_MODE = First Wins
    GEOM_TYPE = Build Polygons
    GROUP_BY = _building_id
    IGNORE_NULLS = No
    JOIN_KEYS = @Value(ifc_unique_id) @Value(ifc_unique_id) AUTO
    MERGE_TYPE = Attributes Only
    PROCESS_DUPS = YES
    REJECT_NULL_MISSING_KEYS = No
    SUPPLIERS_FIRST = No
    MERGED -> AttributeValueMapper
AttributeValueMapper
    LUT = IfcDoor,Door,IfcWindow,Window
    MAPPING_DIRECTION = FORWARD
    SRC = _opening_ifc_feature_type
    VAL_ATTR = fme_feature_type
    -> AttributeManager_10
AttributeManager_10
    ATTR_TABLE:
      SET_TO gml_id = open_@UUID()
      REMOVE ifc_unique_id
      RENAME_SET_VALUE _opening_ifc_unique_id > ifc_unique_id
      RENAME_SET_VALUE _opening_ifc_feature_type > _ifc_feature_type
      SET_TO citygml_lod_name = lod4MultiSurface
      SET_TO citygml_feature_role = opening
    -> Junction_15
    -> FeatureTypeFilter_3
Note: AttributeManager_12 : Input / Building MultiSurface に集約
Junction_15
    -> Junction_14
Note: exterior Window, Door / Junction_15 : Output
Junction_14
    -> AttributeManager_12
Note: #gml_id -> xlink_href / _building_id -> gml_id
AttributeManager_12
    ATTR_TABLE:
      SET_TO xlink_href = #@Value(gml_id)
      REMOVE gml_id
      RENAME_SET_VALUE _building_id > gml_id
      REMOVE _storey_id
      REMOVE _storey_name
      REMOVE citygml_lod_name
      REMOVE gml_parent_id
      REMOVE _clipped
    -> GeometryPropertySetter_9
Note: 理想的には、Buildingのジオメトリとして WallSurface, GroundSurface, RoofSurface 等で囲まれた閉じた立体 (lod4Solid) を作成するのが望ましいが、実際のIFCデータでは屋外壁が連続していない（隙間がある）ことが一般的であることから、lod4MultiSurfaceとした。
GeometryPropertySetter_9
    GQUERY:
      for $geom in //geometry
      where $geom/count(parent::geometry) = 0
      return number($geom/@fme_id)
    OVERWRITE_CHOICE = Yes
    REMOVE_ATTRIBUTE = Yes
    SETTYPE_PARAM = Traits From Attributes
    SRC_ATTRS = xlink_href
    SET -> Aggregator
Aggregator
    ACCUM_ATTRS_NAME = Drop Incoming Attributes
    AGGREGATE_TYPE = Homogeneous Collection (If Possible)
    GROUP_BY = gml_id
    MODE = Geometry - Assemble One Level
    SEP = ,
    AGGREGATE -> AttributeCreator_2
AttributeCreator_2
    ATTR_TABLE = SET_TO citygml_lod_name = lod4MultiSurface
    -> GeometryPropertySetter_13
GeometryPropertySetter_13
    GQUERY:
      for $geom in //geometry
      where $geom/count(parent::geometry) = 0
      return number($geom/@fme_id)
    OVERWRITE_CHOICE = Yes
    REMOVE_ATTRIBUTE = No
    SETTYPE_PARAM = Traits From Attributes
    SRC_ATTRS = citygml_lod_name
    SET -> Building (writer CITYGML_2)
Building (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer,
      citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, uro_building_data_quality_attribute{}.uro_building_data_quality_attribute_uro_src_scale{} xml_buffer, uro_building_data_quality_attribute{}.uro_building_data_quality_attribute_uro_src_scale{}.codeSpace xml_buffer, uro_building_data_quality_attribute{}.uro_building_data_quality_attribute_uro_geometry_src_desc{} xml_buffer, uro_building_data_quality_attribute{}.uro_building_data_quality_attribute_uro_geometry_src_desc{}.codeSpace xml_buffer, uro_building_data_quality_attribute{}.uro_building_data_quality_attribute_uro_thematic_src_desc{} xml_buffer, uro_building_data_quality_attribute{}.uro_building_data_quality_attribute_uro_thematic_src_desc{}.codeSpace xml_buffer, uro_building_data_quality_attribute{}.uro_building_data_quality_attribute_uro_appearance_src_desc{} xml_buffer, uro_building_data_quality_attribute{}.uro_building_data_quality_attribute_uro_appearance_src_desc{}.codeSpace xml_buffer, uro_building_data_quality_attribute{}.uro_building_data_quality_attribute_uro_lod1_height_type xml_buffer, uro_building_data_quality_attribute{}.uro_building_data_quality_attribute_uro_lod1_height_type_codeSpace xml_buffer, uro_building_data_quality_attribute{}.uro_building_data_quality_attribute_uro_lod_type{} xml_char(3), uro_ifc_building_attribute{}.uro_ifc_building_uro_global_id xml_buffer, uro_ifc_building_attribute{}.uro_ifc_building_uro_name xml_buffer, uro_ifc_building_attribute{}.uro_ifc_building_uro_description xml_buffer, uro_ifc_building_attribute{}.uro_ifc_building_uro_object_type xml_buffer, uro_ifc_building_attribute{}.uro_ifc_building_uro_long_name xml_buffer, uro_ifc_building_attribute{}.uro_ifc_building_uro_composition_type xml_char(7), uro_ifc_building_attribute{}.uro_ifc_building_uro_elevation_of_ref_height xml_real64, uro_ifc_building_attribute{}.uro_ifc_building_uro_elevation_of_ref_height_units xml_buffer, uro_ifc_building_attribute{}.uro_ifc_building_uro_elevation_of_terrain xml_real64, uro_ifc_building_attribute{}.uro_ifc_building_uro_elevation_of_terrain_units xml_buffer,
      uro_ifc_building_attribute{}.uro_ifc_building_uro_building_address_xlink_href xml_buffer, uro_ifc_building_attribute{}.uro_ifc_building_element_uro_global_id xml_buffer, uro_ifc_building_attribute{}.uro_ifc_building_element_uro_name xml_buffer, uro_ifc_building_attribute{}.uro_ifc_building_element_uro_description xml_buffer, uro_ifc_building_attribute{}.uro_ifc_building_element_uro_object_type xml_buffer, uro_ifc_building_attribute{}.uro_ifc_building_element_uro_tag xml_buffer, uro_ifc_building_attribute{}.uro_ifc_building_element_uro_element_type xml_buffer, uro_ifc_building_attribute{}.uro_ifc_building_element_uro_element_type_codeSpace xml_buffer, uro_ifc_building_attribute{}.uro_ifc_building_element_uro_predefined_type xml_buffer, uro_ifc_building_attribute{}.uro_ifc_building_element_uro_predefined_type_codeSpace xml_buffer, uro_ifc_building_attribute{}.uro_ifc_building_element_uro_shape_type xml_buffer, uro_ifc_building_attribute{}.uro_ifc_building_element_uro_shape_type_codeSpace xml_buffer, uro_ifc_building_attribute{}.uro_ifc_building_element_uro_number_of_riser xml_int64, uro_ifc_building_attribute{}.uro_ifc_building_element_uro_number_of_treads xml_int64, uro_ifc_building_attribute{}.uro_ifc_building_element_uro_riser_height xml_int64, uro_ifc_building_attribute{}.uro_ifc_building_element_uro_tread_length xml_int64, uro_ifc_building_attribute{}.uro_ifc_building_element_uro_operation_type xml_char(11), uro_ifc_building_attribute{}.uro_ifc_building_element_uro_capacity_by_weight xml_real64, uro_ifc_building_attribute{}.uro_ifc_building_element_uro_capacity_by_weight_units xml_buffer, uro_ifc_building_attribute{}.uro_ifc_building_element_uro_capacity_by_number xml_int64, uro_ifc_building_attribute{}.uro_ifc_building_storey_uro_global_id xml_buffer, uro_ifc_building_attribute{}.uro_ifc_building_storey_uro_name xml_buffer, uro_ifc_building_attribute{}.uro_ifc_building_storey_uro_description xml_buffer, uro_ifc_building_attribute{}.uro_ifc_building_storey_uro_object_type xml_buffer, uro_ifc_building_attribute{}.uro_ifc_building_storey_uro_long_name xml_buffer, uro_ifc_building_attribute{}.uro_ifc_building_storey_uro_composition_type xml_char(7), uro_ifc_building_attribute{}.uro_ifc_building_storey_uro_elevation xml_real64, uro_ifc_building_attribute{}.uro_ifc_building_storey_uro_elevation_units xml_buffer, uro_ifc_building_attribute{}.uro_ifc_classification_reference_uro_location xml_buffer, uro_ifc_building_attribute{}.uro_ifc_classification_reference_uro_item_reference xml_buffer,
      uro_ifc_building_attribute{}.uro_ifc_classification_reference_uro_item_reference_codeSpace xml_buffer, uro_ifc_building_attribute{}.uro_ifc_classification_reference_uro_name xml_buffer, uro_ifc_building_attribute{}.uro_ifc_classification_reference_uro_name_codeSpace xml_buffer, uro_ifc_building_attribute{}.uro_ifc_classification_reference_uro_reference_source_uro_ifc_classification_uro_source xml_buffer, uro_ifc_building_attribute{}.uro_ifc_classification_reference_uro_reference_source_uro_ifc_classification_uro_edition xml_buffer, uro_ifc_building_attribute{}.uro_ifc_classification_reference_uro_reference_source_uro_ifc_classification_uro_edition_date xml_date, uro_ifc_building_attribute{}.uro_ifc_classification_reference_uro_reference_source_uro_ifc_classification_uro_name xml_buffer, uro_ifc_building_attribute{}.uro_ifc_coordinate_reference_system_uro_name xml_buffer, uro_ifc_building_attribute{}.uro_ifc_coordinate_reference_system_uro_description xml_buffer, uro_ifc_building_attribute{}.uro_ifc_coordinate_reference_system_uro_geodetic_datum xml_buffer, uro_ifc_building_attribute{}.uro_ifc_coordinate_reference_system_uro_vertical_datum xml_buffer, uro_ifc_building_attribute{}.uro_ifc_curtain_wall_uro_global_id xml_buffer, uro_ifc_building_attribute{}.uro_ifc_curtain_wall_uro_name xml_buffer, uro_ifc_building_attribute{}.uro_ifc_curtain_wall_uro_description xml_buffer, uro_ifc_building_attribute{}.uro_ifc_curtain_wall_uro_object_type xml_buffer, uro_ifc_building_attribute{}.uro_ifc_curtain_wall_uro_tag xml_buffer, uro_ifc_building_attribute{}.uro_ifc_curtain_wall_uro_element_type xml_buffer, uro_ifc_building_attribute{}.uro_ifc_curtain_wall_uro_element_type_codeSpace xml_buffer, uro_ifc_building_attribute{}.uro_ifc_curtain_wall_uro_predefined_type xml_buffer, uro_ifc_building_attribute{}.uro_ifc_curtain_wall_uro_predefined_type_codeSpace xml_buffer, uro_ifc_building_attribute{}.uro_ifc_curtain_wall_uro_shape_type xml_buffer, uro_ifc_building_attribute{}.uro_ifc_curtain_wall_uro_shape_type_codeSpace xml_buffer, uro_ifc_building_attribute{}.uro_ifc_curtain_wall_uro_number_of_riser xml_int64, uro_ifc_building_attribute{}.uro_ifc_curtain_wall_uro_number_of_treads xml_int64, uro_ifc_building_attribute{}.uro_ifc_curtain_wall_uro_riser_height xml_int64, uro_ifc_building_attribute{}.uro_ifc_curtain_wall_uro_tread_length xml_int64, uro_ifc_building_attribute{}.uro_ifc_curtain_wall_uro_operation_type xml_char(11), uro_ifc_building_attribute{}.uro_ifc_curtain_wall_uro_capacity_by_weight xml_real64, uro_ifc_building_attribute{}.uro_ifc_curtain_wall_uro_capacity_by_weight_units xml_buffer, uro_ifc_building_attribute{}.uro_ifc_curtain_wall_uro_capacity_by_number xml_int64,
      uro_ifc_building_attribute{}.uro_ifc_door_uro_global_id xml_buffer, uro_ifc_building_attribute{}.uro_ifc_door_uro_name xml_buffer, uro_ifc_building_attribute{}.uro_ifc_door_uro_description xml_buffer, uro_ifc_building_attribute{}.uro_ifc_door_uro_object_type xml_buffer, uro_ifc_building_attribute{}.uro_ifc_door_uro_tag xml_buffer, uro_ifc_building_attribute{}.uro_ifc_door_uro_element_type xml_buffer, uro_ifc_building_attribute{}.uro_ifc_door_uro_element_type_codeSpace xml_buffer, uro_ifc_building_attribute{}.uro_ifc_door_uro_predefined_type xml_buffer, uro_ifc_building_attribute{}.uro_ifc_door_uro_predefined_type_codeSpace xml_buffer, uro_ifc_building_attribute{}.uro_ifc_door_uro_shape_type xml_buffer, uro_ifc_building_attribute{}.uro_ifc_door_uro_shape_type_codeSpace xml_buffer, uro_ifc_building_attribute{}.uro_ifc_door_uro_number_of_riser xml_int64, uro_ifc_building_attribute{}.uro_ifc_door_uro_number_of_treads xml_int64, uro_ifc_building_attribute{}.uro_ifc_door_uro_riser_height xml_int64, uro_ifc_building_attribute{}.uro_ifc_door_uro_tread_length xml_int64, uro_ifc_building_attribute{}.uro_ifc_door_uro_operation_type xml_char(11), uro_ifc_building_attribute{}.uro_ifc_door_uro_capacity_by_weight xml_real64, uro_ifc_building_attribute{}.uro_ifc_door_uro_capacity_by_weight_units xml_buffer, uro_ifc_building_attribute{}.uro_ifc_door_uro_capacity_by_number xml_int64, uro_ifc_building_attribute{}.uro_ifc_door_uro_overall_height xml_real64, uro_ifc_building_attribute{}.uro_ifc_door_uro_overall_height_units xml_buffer, uro_ifc_building_attribute{}.uro_ifc_door_uro_overall_width xml_real64, uro_ifc_building_attribute{}.uro_ifc_door_uro_overall_width_units xml_buffer, uro_ifc_building_attribute{}.uro_ifc_furnishing_element_uro_global_id xml_buffer, uro_ifc_building_attribute{}.uro_ifc_furnishing_element_uro_name xml_buffer, uro_ifc_building_attribute{}.uro_ifc_furnishing_element_uro_description xml_buffer, uro_ifc_building_attribute{}.uro_ifc_furnishing_element_uro_object_type xml_buffer, uro_ifc_building_attribute{}.uro_ifc_furnishing_element_uro_tag xml_buffer, uro_ifc_building_attribute{}.uro_ifc_map_conversion_uro_source_crs_uro_crs_uro_ifc_projected_crs_uro_name xml_buffer, uro_ifc_building_attribute{}.uro_ifc_map_conversion_uro_source_crs_uro_crs_uro_ifc_projected_crs_uro_description xml_buffer,
      uro_ifc_building_attribute{}.uro_ifc_map_conversion_uro_source_crs_uro_crs_uro_ifc_projected_crs_uro_geodetic_datum xml_buffer, uro_ifc_building_attribute{}.uro_ifc_map_conversion_uro_source_crs_uro_crs_uro_ifc_projected_crs_uro_vertical_datum xml_buffer, uro_ifc_building_attribute{}.uro_ifc_map_conversion_uro_source_crs_uro_crs_uro_ifc_projected_crs_uro_map_unit xml_buffer, uro_ifc_building_attribute{}.uro_ifc_map_conversion_uro_source_crs_uro_crs_uro_ifc_projected_crs_uro_map_projection xml_buffer, uro_ifc_building_attribute{}.uro_ifc_map_conversion_uro_source_crs_uro_crs_uro_ifc_projected_crs_uro_map_zone xml_buffer, uro_ifc_building_attribute{}.uro_ifc_map_conversion_uro_source_crs_uro_crs_uro_ifc_coordinate_reference_system_uro_name xml_buffer, uro_ifc_building_attribute{}.uro_ifc_map_conversion_uro_source_crs_uro_crs_uro_ifc_coordinate_reference_system_uro_description xml_buffer, uro_ifc_building_attribute{}.uro_ifc_map_conversion_uro_source_crs_uro_crs_uro_ifc_coordinate_reference_system_uro_geodetic_datum xml_buffer, uro_ifc_building_attribute{}.uro_ifc_map_conversion_uro_source_crs_uro_crs_uro_ifc_coordinate_reference_system_uro_vertical_datum xml_buffer, uro_ifc_building_attribute{}.uro_ifc_map_conversion_uro_source_crs_uro_context_uro_ifc_geometric_representation_context_uro_context_identifier xml_buffer, uro_ifc_building_attribute{}.uro_ifc_map_conversion_uro_source_crs_uro_context_uro_ifc_geometric_representation_context_uro_context_type xml_buffer, uro_ifc_building_attribute{}.uro_ifc_map_conversion_uro_source_crs_uro_context_uro_ifc_geometric_representation_context_uro_coordinate_space_dimension xml_int64, uro_ifc_building_attribute{}.uro_ifc_map_conversion_uro_source_crs_uro_context_uro_ifc_geometric_representation_context_uro_precision xml_real64, uro_ifc_building_attribute{}.uro_ifc_map_conversion_uro_source_crs_uro_context_uro_ifc_geometric_representation_context_uro_true_north xml_real64, uro_ifc_building_attribute{}.uro_ifc_map_conversion_uro_target_crs_uro_ifc_projected_crs_uro_name xml_buffer, uro_ifc_building_attribute{}.uro_ifc_map_conversion_uro_target_crs_uro_ifc_projected_crs_uro_description xml_buffer, uro_ifc_building_attribute{}.uro_ifc_map_conversion_uro_target_crs_uro_ifc_projected_crs_uro_geodetic_datum xml_buffer, uro_ifc_building_attribute{}.uro_ifc_map_conversion_uro_target_crs_uro_ifc_projected_crs_uro_vertical_datum xml_buffer, uro_ifc_building_attribute{}.uro_ifc_map_conversion_uro_target_crs_uro_ifc_projected_crs_uro_map_unit xml_buffer, uro_ifc_building_attribute{}.uro_ifc_map_conversion_uro_target_crs_uro_ifc_projected_crs_uro_map_projection xml_buffer, uro_ifc_building_attribute{}.uro_ifc_map_conversion_uro_target_crs_uro_ifc_projected_crs_uro_map_zone xml_buffer, uro_ifc_building_attribute{}.uro_ifc_map_conversion_uro_target_crs_uro_ifc_coordinate_reference_system_uro_name xml_buffer, uro_ifc_building_attribute{}.uro_ifc_map_conversion_uro_target_crs_uro_ifc_coordinate_reference_system_uro_description xml_buffer, uro_ifc_building_attribute{}.uro_ifc_map_conversion_uro_target_crs_uro_ifc_coordinate_reference_system_uro_geodetic_datum xml_buffer, uro_ifc_building_attribute{}.uro_ifc_map_conversion_uro_target_crs_uro_ifc_coordinate_reference_system_uro_vertical_datum xml_buffer, uro_ifc_building_attribute{}.uro_ifc_map_conversion_uro_eastings xml_buffer, uro_ifc_building_attribute{}.uro_ifc_map_conversion_uro_northings xml_buffer, uro_ifc_building_attribute{}.uro_ifc_map_conversion_uro_orthogonal_height xml_real64, uro_ifc_building_attribute{}.uro_ifc_map_conversion_uro_orthogonal_height_units xml_buffer, uro_ifc_building_attribute{}.uro_ifc_map_conversion_uro_x_axis_abscissa xml_real64,
      uro_ifc_building_attribute{}.uro_ifc_map_conversion_uro_x_axis_ordinate xml_real64, uro_ifc_building_attribute{}.uro_ifc_map_conversion_uro_scale xml_real64, uro_ifc_building_attribute{}.uro_ifc_opening_element_uro_global_id xml_buffer, uro_ifc_building_attribute{}.uro_ifc_opening_element_uro_name xml_buffer, uro_ifc_building_attribute{}.uro_ifc_opening_element_uro_description xml_buffer, uro_ifc_building_attribute{}.uro_ifc_opening_element_uro_object_type xml_buffer, uro_ifc_building_attribute{}.uro_ifc_opening_element_uro_tag xml_buffer, uro_ifc_building_attribute{}.uro_ifc_opening_element_uro_nominal_area xml_real64, uro_ifc_building_attribute{}.uro_ifc_opening_element_uro_nominal_area_units xml_buffer, uro_ifc_building_attribute{}.uro_ifc_opening_element_uro_nominal_volume xml_real64, uro_ifc_building_attribute{}.uro_ifc_opening_element_uro_nominal_volume_units xml_buffer, uro_ifc_building_attribute{}.uro_ifc_project_uro_global_id xml_buffer, uro_ifc_building_attribute{}.uro_ifc_project_uro_name xml_buffer, uro_ifc_building_attribute{}.uro_ifc_project_uro_description xml_buffer, uro_ifc_building_attribute{}.uro_ifc_project_uro_object_type xml_buffer, uro_ifc_building_attribute{}.uro_ifc_project_uro_long_name xml_buffer, uro_ifc_building_attribute{}.uro_ifc_project_uro_phase xml_buffer, uro_ifc_building_attribute{}.uro_ifc_project_uro_representation_contexts_uro_ifc_geometric_representation_context_uro_context_identifier xml_buffer, uro_ifc_building_attribute{}.uro_ifc_project_uro_representation_contexts_uro_ifc_geometric_representation_context_uro_context_type xml_buffer, uro_ifc_building_attribute{}.uro_ifc_project_uro_representation_contexts_uro_ifc_geometric_representation_context_uro_coordinate_space_dimension xml_int64, uro_ifc_building_attribute{}.uro_ifc_project_uro_representation_contexts_uro_ifc_geometric_representation_context_uro_precision xml_real64, uro_ifc_building_attribute{}.uro_ifc_project_uro_representation_contexts_uro_ifc_geometric_representation_context_uro_true_north xml_real64, uro_ifc_building_attribute{}.uro_ifc_project_uro_units_in_context{}.uro_ifc_unit_uro_dimensions xml_int64, uro_ifc_building_attribute{}.uro_ifc_project_uro_units_in_context{}.uro_ifc_unit_uro_unit_type xml_char(28), uro_ifc_building_attribute{}.uro_ifc_project_uro_units_in_context{}.uro_ifc_unit_uro_perfix xml_buffer, uro_ifc_building_attribute{}.uro_ifc_project_uro_units_in_context{}.uro_ifc_unit_uro_name xml_buffer, uro_ifc_building_attribute{}.uro_ifc_projected_crs_uro_name xml_buffer, uro_ifc_building_attribute{}.uro_ifc_projected_crs_uro_description xml_buffer, uro_ifc_building_attribute{}.uro_ifc_projected_crs_uro_geodetic_datum xml_buffer, uro_ifc_building_attribute{}.uro_ifc_projected_crs_uro_vertical_datum xml_buffer,
      uro_ifc_building_attribute{}.uro_ifc_projected_crs_uro_map_unit xml_buffer, uro_ifc_building_attribute{}.uro_ifc_projected_crs_uro_map_projection xml_buffer, uro_ifc_building_attribute{}.uro_ifc_projected_crs_uro_map_zone xml_buffer, uro_ifc_building_attribute{}.uro_ifc_pset_building_common_uro_building_id xml_real64, uro_ifc_building_attribute{}.uro_ifc_pset_building_common_uro_building_id_units xml_buffer, uro_ifc_building_attribute{}.uro_ifc_pset_building_common_uro_is_permanent_id xml_real64, uro_ifc_building_attribute{}.uro_ifc_pset_building_common_uro_is_permanent_id_units xml_buffer, uro_ifc_building_attribute{}.uro_ifc_pset_building_common_uro_main_fire_use xml_buffer, uro_ifc_building_attribute{}.uro_ifc_pset_building_common_uro_ancillary_fire_use xml_buffer, uro_ifc_building_attribute{}.uro_ifc_pset_building_common_uro_sprinkler_protection xml_boolean, uro_ifc_building_attribute{}.uro_ifc_pset_building_common_uro_sprinkler_protection_automatic xml_boolean, uro_ifc_building_attribute{}.uro_ifc_pset_building_common_uro_occupancy_type xml_buffer, uro_ifc_building_attribute{}.uro_ifc_pset_building_common_uro_occupancy_type_codeSpace xml_buffer, uro_ifc_building_attribute{}.uro_ifc_pset_building_common_uro_gross_planned_area xml_real64, uro_ifc_building_attribute{}.uro_ifc_pset_building_common_uro_gross_planned_area_units xml_buffer, uro_ifc_building_attribute{}.uro_ifc_pset_building_common_uro_number_of_storeys xml_int64, uro_ifc_building_attribute{}.uro_ifc_pset_building_common_uro_year_of_construction xml_buffer, uro_ifc_building_attribute{}.uro_ifc_pset_building_common_uro_is_landmarked xml_boolean, uro_ifc_building_attribute{}.uro_ifc_pset_door_common_uro_reference xml_buffer, uro_ifc_building_attribute{}.uro_ifc_pset_door_common_uro_acoustic_rating xml_buffer, uro_ifc_building_attribute{}.uro_ifc_pset_door_common_uro_firerating xml_buffer, uro_ifc_building_attribute{}.uro_ifc_pset_door_common_uro_security_rating xml_buffer, uro_ifc_building_attribute{}.uro_ifc_pset_door_common_uro_is_external xml_boolean, uro_ifc_building_attribute{}.uro_ifc_pset_door_common_uro_infiltration xml_real64, uro_ifc_building_attribute{}.uro_ifc_pset_door_common_uro_thermal_transmittance xml_real64, uro_ifc_building_attribute{}.uro_ifc_pset_door_common_uro_glazing_area_fraction xml_real64, uro_ifc_building_attribute{}.uro_ifc_pset_door_common_uro_handicap_accessible xml_real64, uro_ifc_building_attribute{}.uro_ifc_pset_door_common_uro_fire_exit xml_boolean, uro_ifc_building_attribute{}.uro_ifc_pset_door_common_uro_self_closing xml_real64, uro_ifc_building_attribute{}.uro_ifc_pset_door_common_uro_smoke_stop xml_boolean,
      uro_ifc_building_attribute{}.uro_ifc_pset_opening_element_common_uro_reference xml_buffer, uro_ifc_building_attribute{}.uro_ifc_pset_opening_element_common_uro_purpose xml_buffer, uro_ifc_building_attribute{}.uro_ifc_pset_opening_element_common_uro_fire_exit xml_boolean, uro_ifc_building_attribute{}.uro_ifc_pset_opening_element_common_uro_protected_opening xml_boolean, uro_ifc_building_attribute{}.uro_ifc_pset_opening_element_common_uro_parallel_jambs xml_boolean, uro_ifc_building_attribute{}.uro_ifc_pset_site_common_uro_buildable_area xml_real64, uro_ifc_building_attribute{}.uro_ifc_pset_site_common_uro_buildable_area_units xml_buffer, uro_ifc_building_attribute{}.uro_ifc_pset_site_common_uro_total_area xml_real64, uro_ifc_building_attribute{}.uro_ifc_pset_site_common_uro_total_area_units xml_buffer, uro_ifc_building_attribute{}.uro_ifc_pset_site_common_uro_building_height_limit xml_real64, uro_ifc_building_attribute{}.uro_ifc_pset_site_common_uro_building_height_limit_units xml_buffer, uro_ifc_building_attribute{}.uro_ifc_pset_space_common_uro_reference xml_buffer, uro_ifc_building_attribute{}.uro_ifc_pset_space_common_uro_category xml_buffer, uro_ifc_building_attribute{}.uro_ifc_pset_space_common_uro_category_codeSpace xml_buffer, uro_ifc_building_attribute{}.uro_ifc_pset_space_common_uro_floor_covering xml_buffer, uro_ifc_building_attribute{}.uro_ifc_pset_space_common_uro_wall_covering xml_buffer, uro_ifc_building_attribute{}.uro_ifc_pset_space_common_uro_ceiling_covering xml_buffer, uro_ifc_building_attribute{}.uro_ifc_pset_space_common_uro_skirting_covering xml_buffer, uro_ifc_building_attribute{}.uro_ifc_pset_space_common_uro_gross_planned_area xml_real64, uro_ifc_building_attribute{}.uro_ifc_pset_space_common_uro_gross_planned_area_units xml_buffer, uro_ifc_building_attribute{}.uro_ifc_pset_space_common_uro_net_planned_area xml_real64, uro_ifc_building_attribute{}.uro_ifc_pset_space_common_uro_net_planned_area_units xml_buffer, uro_ifc_building_attribute{}.uro_ifc_pset_space_common_uro_publicly_accessible xml_boolean, uro_ifc_building_attribute{}.uro_ifc_pset_space_common_uro_handicap_accessible xml_boolean, uro_ifc_building_attribute{}.uro_ifc_pset_space_common_uro_concealed_flooring xml_boolean, uro_ifc_building_attribute{}.uro_ifc_pset_space_common_uro_concealed_ceiling xml_boolean, uro_ifc_building_attribute{}.uro_ifc_pset_window_common_uro_reference xml_buffer, uro_ifc_building_attribute{}.uro_ifc_pset_window_common_uro_acoustic_rating xml_buffer, uro_ifc_building_attribute{}.uro_ifc_pset_window_common_uro_firerating xml_buffer, uro_ifc_building_attribute{}.uro_ifc_pset_window_common_uro_security_rating xml_buffer,
      uro_ifc_building_attribute{}.uro_ifc_pset_window_common_uro_is_external xml_boolean, uro_ifc_building_attribute{}.uro_ifc_pset_window_common_uro_infiltration xml_real64, uro_ifc_building_attribute{}.uro_ifc_pset_window_common_uro_thermal_transmittance xml_real64, uro_ifc_building_attribute{}.uro_ifc_pset_window_common_uro_glazing_area_fraction xml_real64, uro_ifc_building_attribute{}.uro_ifc_pset_window_common_uro_smoke_stop xml_boolean, uro_ifc_building_attribute{}.uro_ifc_site_uro_global_id xml_buffer, uro_ifc_building_attribute{}.uro_ifc_site_uro_name xml_buffer, uro_ifc_building_attribute{}.uro_ifc_site_uro_description xml_buffer, uro_ifc_building_attribute{}.uro_ifc_site_uro_object_type xml_buffer, uro_ifc_building_attribute{}.uro_ifc_site_uro_long_name xml_buffer, uro_ifc_building_attribute{}.uro_ifc_site_uro_composition_type xml_char(7), uro_ifc_building_attribute{}.uro_ifc_site_uro_ref_longitude xml_real64, uro_ifc_building_attribute{}.uro_ifc_site_uro_ref_latitude xml_real64, uro_ifc_building_attribute{}.uro_ifc_site_uro_ref_elevation xml_real64, uro_ifc_building_attribute{}.uro_ifc_site_uro_ref_elevation_units xml_buffer, uro_ifc_building_attribute{}.uro_ifc_site_uro_land_title_number xml_buffer, uro_ifc_building_attribute{}.uro_ifc_site_uro_site_address_xlink_href xml_buffer, uro_ifc_building_attribute{}.uro_ifc_space_uro_global_id xml_buffer, uro_ifc_building_attribute{}.uro_ifc_space_uro_name xml_buffer, uro_ifc_building_attribute{}.uro_ifc_space_uro_description xml_buffer, uro_ifc_building_attribute{}.uro_ifc_space_uro_object_type xml_buffer, uro_ifc_building_attribute{}.uro_ifc_space_uro_long_name xml_buffer, uro_ifc_building_attribute{}.uro_ifc_space_uro_composition_type xml_char(7), uro_ifc_building_attribute{}.uro_ifc_space_uro_interioror_exterior_space xml_char(10), uro_ifc_building_attribute{}.uro_ifc_space_uro_elevation_with_flooring xml_real64, uro_ifc_building_attribute{}.uro_ifc_space_uro_elevation_with_flooring_units xml_buffer, uro_ifc_building_attribute{}.uro_ifc_space_base_quantity_uro_nominal_height xml_real64, uro_ifc_building_attribute{}.uro_ifc_space_base_quantity_uro_nominal_height_units xml_buffer, uro_ifc_building_attribute{}.uro_ifc_space_base_quantity_uro_clear_height xml_real64, uro_ifc_building_attribute{}.uro_ifc_space_base_quantity_uro_clear_height_units xml_buffer,
      uro_ifc_building_attribute{}.uro_ifc_space_base_quantity_uro_finish_ceiling_height xml_real64, uro_ifc_building_attribute{}.uro_ifc_space_base_quantity_uro_finish_ceiling_height_units xml_buffer, uro_ifc_building_attribute{}.uro_ifc_space_base_quantity_uro_gross_perimeter xml_real64, uro_ifc_building_attribute{}.uro_ifc_space_base_quantity_uro_gross_perimeter_units xml_buffer, uro_ifc_building_attribute{}.uro_ifc_space_base_quantity_uro_net_perimeter xml_real64, uro_ifc_building_attribute{}.uro_ifc_space_base_quantity_uro_net_perimeter_units xml_buffer, uro_ifc_building_attribute{}.uro_ifc_space_base_quantity_uro_gross_ceiling_area xml_real64, uro_ifc_building_attribute{}.uro_ifc_space_base_quantity_uro_gross_ceiling_area_units xml_buffer, uro_ifc_building_attribute{}.uro_ifc_space_base_quantity_uro_gross_floor_area xml_real64, uro_ifc_building_attribute{}.uro_ifc_space_base_quantity_uro_gross_floor_area_units xml_buffer, uro_ifc_building_attribute{}.uro_ifc_space_base_quantity_uro_net_ceiling_area xml_real64, uro_ifc_building_attribute{}.uro_ifc_space_base_quantity_uro_net_ceiling_area_units xml_buffer, uro_ifc_building_attribute{}.uro_ifc_space_base_quantity_uro_net_floor_area xml_real64, uro_ifc_building_attribute{}.uro_ifc_space_base_quantity_uro_net_floor_area_units xml_buffer, uro_ifc_building_attribute{}.uro_ifc_space_base_quantity_uro_gross_wall_area xml_real64, uro_ifc_building_attribute{}.uro_ifc_space_base_quantity_uro_gross_wall_area_units xml_buffer, uro_ifc_building_attribute{}.uro_ifc_space_base_quantity_uro_net_wall_area xml_real64, uro_ifc_building_attribute{}.uro_ifc_space_base_quantity_uro_net_wall_area_units xml_buffer, uro_ifc_building_attribute{}.uro_ifc_space_base_quantity_uro_gross_volume xml_real64, uro_ifc_building_attribute{}.uro_ifc_space_base_quantity_uro_gross_volume_units xml_buffer, uro_ifc_building_attribute{}.uro_ifc_space_base_quantity_uro_net_volume xml_real64, uro_ifc_building_attribute{}.uro_ifc_space_base_quantity_uro_net_volume_units xml_buffer, uro_ifc_building_attribute{}.uro_ifc_wall_uro_global_id xml_buffer, uro_ifc_building_attribute{}.uro_ifc_wall_uro_name xml_buffer, uro_ifc_building_attribute{}.uro_ifc_wall_uro_description xml_buffer, uro_ifc_building_attribute{}.uro_ifc_wall_uro_object_type xml_buffer, uro_ifc_building_attribute{}.uro_ifc_wall_uro_tag xml_buffer, uro_ifc_building_attribute{}.uro_ifc_wall_uro_element_type xml_buffer, uro_ifc_building_attribute{}.uro_ifc_wall_uro_element_type_codeSpace xml_buffer, uro_ifc_building_attribute{}.uro_ifc_wall_uro_predefined_type xml_buffer,
      uro_ifc_building_attribute{}.uro_ifc_wall_uro_predefined_type_codeSpace xml_buffer, uro_ifc_building_attribute{}.uro_ifc_wall_uro_shape_type xml_buffer, uro_ifc_building_attribute{}.uro_ifc_wall_uro_shape_type_codeSpace xml_buffer, uro_ifc_building_attribute{}.uro_ifc_wall_uro_number_of_riser xml_int64, uro_ifc_building_attribute{}.uro_ifc_wall_uro_number_of_treads xml_int64, uro_ifc_building_attribute{}.uro_ifc_wall_uro_riser_height xml_int64, uro_ifc_building_attribute{}.uro_ifc_wall_uro_tread_length xml_int64, uro_ifc_building_attribute{}.uro_ifc_wall_uro_operation_type xml_char(11), uro_ifc_building_attribute{}.uro_ifc_wall_uro_capacity_by_weight xml_real64, uro_ifc_building_attribute{}.uro_ifc_wall_uro_capacity_by_weight_units xml_buffer, uro_ifc_building_attribute{}.uro_ifc_wall_uro_capacity_by_number xml_int64, uro_ifc_building_attribute{}.uro_ifc_wall_uro_nominal_length xml_real64, uro_ifc_building_attribute{}.uro_ifc_wall_uro_nominal_length_units xml_buffer, uro_ifc_building_attribute{}.uro_ifc_wall_uro_nominal_width xml_real64, uro_ifc_building_attribute{}.uro_ifc_wall_uro_nominal_width_units xml_buffer, uro_ifc_building_attribute{}.uro_ifc_wall_uro_nominal_height xml_real64, uro_ifc_building_attribute{}.uro_ifc_wall_uro_nominal_height_units xml_buffer, uro_ifc_building_attribute{}.uro_ifc_wall_uro_gross_foot_print_area xml_real64, uro_ifc_building_attribute{}.uro_ifc_wall_uro_gross_foot_print_area_units xml_buffer, uro_ifc_building_attribute{}.uro_ifc_wall_uro_net_foot_print_area xml_real64, uro_ifc_building_attribute{}.uro_ifc_wall_uro_net_foot_print_area_units xml_buffer, uro_ifc_building_attribute{}.uro_ifc_wall_uro_gross_side_area xml_real64, uro_ifc_building_attribute{}.uro_ifc_wall_uro_gross_side_area_units xml_buffer, uro_ifc_building_attribute{}.uro_ifc_wall_uro_net_side_area xml_real64, uro_ifc_building_attribute{}.uro_ifc_wall_uro_net_side_area_units xml_buffer, uro_ifc_building_attribute{}.uro_ifc_wall_uro_gross_side_area_left xml_real64, uro_ifc_building_attribute{}.uro_ifc_wall_uro_gross_side_area_left_units xml_buffer, uro_ifc_building_attribute{}.uro_ifc_wall_uro_net_side_area_left xml_real64, uro_ifc_building_attribute{}.uro_ifc_wall_uro_net_side_area_left_units xml_buffer, uro_ifc_building_attribute{}.uro_ifc_wall_uro_gross_side_area_right xml_real64,
      uro_ifc_building_attribute{}.uro_ifc_wall_uro_gross_side_area_right_units xml_buffer, uro_ifc_building_attribute{}.uro_ifc_wall_uro_net_side_area_right xml_real64, uro_ifc_building_attribute{}.uro_ifc_wall_uro_net_side_area_right_units xml_buffer, uro_ifc_building_attribute{}.uro_ifc_wall_uro_gross_volume xml_real64, uro_ifc_building_attribute{}.uro_ifc_wall_uro_gross_volume_units xml_buffer, uro_ifc_building_attribute{}.uro_ifc_wall_uro_net_volume xml_real64, uro_ifc_building_attribute{}.uro_ifc_wall_uro_net_volume_units xml_buffer, uro_ifc_building_attribute{}.uro_ifc_wall_standard_case_uro_global_id xml_buffer, uro_ifc_building_attribute{}.uro_ifc_wall_standard_case_uro_name xml_buffer, uro_ifc_building_attribute{}.uro_ifc_wall_standard_case_uro_description xml_buffer, uro_ifc_building_attribute{}.uro_ifc_wall_standard_case_uro_object_type xml_buffer, uro_ifc_building_attribute{}.uro_ifc_wall_standard_case_uro_tag xml_buffer, uro_ifc_building_attribute{}.uro_ifc_wall_standard_case_uro_element_type xml_buffer, uro_ifc_building_attribute{}.uro_ifc_wall_standard_case_uro_element_type_codeSpace xml_buffer, uro_ifc_building_attribute{}.uro_ifc_wall_standard_case_uro_predefined_type xml_buffer, uro_ifc_building_attribute{}.uro_ifc_wall_standard_case_uro_predefined_type_codeSpace xml_buffer, uro_ifc_building_attribute{}.uro_ifc_wall_standard_case_uro_shape_type xml_buffer, uro_ifc_building_attribute{}.uro_ifc_wall_standard_case_uro_shape_type_codeSpace xml_buffer, uro_ifc_building_attribute{}.uro_ifc_wall_standard_case_uro_number_of_riser xml_int64, uro_ifc_building_attribute{}.uro_ifc_wall_standard_case_uro_number_of_treads xml_int64, uro_ifc_building_attribute{}.uro_ifc_wall_standard_case_uro_riser_height xml_int64, uro_ifc_building_attribute{}.uro_ifc_wall_standard_case_uro_tread_length xml_int64, uro_ifc_building_attribute{}.uro_ifc_wall_standard_case_uro_operation_type xml_char(11), uro_ifc_building_attribute{}.uro_ifc_wall_standard_case_uro_capacity_by_weight xml_real64, uro_ifc_building_attribute{}.uro_ifc_wall_standard_case_uro_capacity_by_weight_units xml_buffer, uro_ifc_building_attribute{}.uro_ifc_wall_standard_case_uro_capacity_by_number xml_int64, uro_ifc_building_attribute{}.uro_ifc_wall_standard_case_uro_nominal_length xml_real64, uro_ifc_building_attribute{}.uro_ifc_wall_standard_case_uro_nominal_length_units xml_buffer, uro_ifc_building_attribute{}.uro_ifc_wall_standard_case_uro_nominal_width xml_real64, uro_ifc_building_attribute{}.uro_ifc_wall_standard_case_uro_nominal_width_units xml_buffer,
      uro_ifc_building_attribute{}.uro_ifc_wall_standard_case_uro_nominal_height xml_real64, uro_ifc_building_attribute{}.uro_ifc_wall_standard_case_uro_nominal_height_units xml_buffer, uro_ifc_building_attribute{}.uro_ifc_wall_standard_case_uro_gross_foot_print_area xml_real64, uro_ifc_building_attribute{}.uro_ifc_wall_standard_case_uro_gross_foot_print_area_units xml_buffer, uro_ifc_building_attribute{}.uro_ifc_wall_standard_case_uro_net_foot_print_area xml_real64, uro_ifc_building_attribute{}.uro_ifc_wall_standard_case_uro_net_foot_print_area_units xml_buffer, uro_ifc_building_attribute{}.uro_ifc_wall_standard_case_uro_gross_side_area xml_real64, uro_ifc_building_attribute{}.uro_ifc_wall_standard_case_uro_gross_side_area_units xml_buffer, uro_ifc_building_attribute{}.uro_ifc_wall_standard_case_uro_net_side_area xml_real64, uro_ifc_building_attribute{}.uro_ifc_wall_standard_case_uro_net_side_area_units xml_buffer, uro_ifc_building_attribute{}.uro_ifc_wall_standard_case_uro_gross_side_area_left xml_real64, uro_ifc_building_attribute{}.uro_ifc_wall_standard_case_uro_gross_side_area_left_units xml_buffer, uro_ifc_building_attribute{}.uro_ifc_wall_standard_case_uro_net_side_area_left xml_real64, uro_ifc_building_attribute{}.uro_ifc_wall_standard_case_uro_net_side_area_left_units xml_buffer, uro_ifc_building_attribute{}.uro_ifc_wall_standard_case_uro_gross_side_area_right xml_real64, uro_ifc_building_attribute{}.uro_ifc_wall_standard_case_uro_gross_side_area_right_units xml_buffer, uro_ifc_building_attribute{}.uro_ifc_wall_standard_case_uro_net_side_area_right xml_real64, uro_ifc_building_attribute{}.uro_ifc_wall_standard_case_uro_net_side_area_right_units xml_buffer, uro_ifc_building_attribute{}.uro_ifc_wall_standard_case_uro_gross_volume xml_real64, uro_ifc_building_attribute{}.uro_ifc_wall_standard_case_uro_gross_volume_units xml_buffer, uro_ifc_building_attribute{}.uro_ifc_wall_standard_case_uro_net_volume xml_real64, uro_ifc_building_attribute{}.uro_ifc_wall_standard_case_uro_net_volume_units xml_buffer, uro_ifc_building_attribute{}.uro_ifc_window_uro_global_id xml_buffer, uro_ifc_building_attribute{}.uro_ifc_window_uro_name xml_buffer, uro_ifc_building_attribute{}.uro_ifc_window_uro_description xml_buffer, uro_ifc_building_attribute{}.uro_ifc_window_uro_object_type xml_buffer, uro_ifc_building_attribute{}.uro_ifc_window_uro_tag xml_buffer, uro_ifc_building_attribute{}.uro_ifc_window_uro_element_type xml_buffer, uro_ifc_building_attribute{}.uro_ifc_window_uro_element_type_codeSpace xml_buffer, uro_ifc_building_attribute{}.uro_ifc_window_uro_predefined_type xml_buffer,
      uro_ifc_building_attribute{}.uro_ifc_window_uro_predefined_type_codeSpace xml_buffer, uro_ifc_building_attribute{}.uro_ifc_window_uro_shape_type xml_buffer, uro_ifc_building_attribute{}.uro_ifc_window_uro_shape_type_codeSpace xml_buffer, uro_ifc_building_attribute{}.uro_ifc_window_uro_number_of_riser xml_int64, uro_ifc_building_attribute{}.uro_ifc_window_uro_number_of_treads xml_int64, uro_ifc_building_attribute{}.uro_ifc_window_uro_riser_height xml_int64, uro_ifc_building_attribute{}.uro_ifc_window_uro_tread_length xml_int64, uro_ifc_building_attribute{}.uro_ifc_window_uro_operation_type xml_char(11), uro_ifc_building_attribute{}.uro_ifc_window_uro_capacity_by_weight xml_real64, uro_ifc_building_attribute{}.uro_ifc_window_uro_capacity_by_weight_units xml_buffer, uro_ifc_building_attribute{}.uro_ifc_window_uro_capacity_by_number xml_int64, uro_ifc_building_attribute{}.uro_ifc_window_uro_overall_height xml_real64, uro_ifc_building_attribute{}.uro_ifc_window_uro_overall_height_units xml_buffer, uro_ifc_building_attribute{}.uro_ifc_window_uro_overall_width xml_real64, uro_ifc_building_attribute{}.uro_ifc_window_uro_overall_width_units xml_buffer
PLATEAU.IfcReprojector_11
    DEST_COORDSYS = $(DEST_COORDSYS)
    LENGTH_MULTIPLIER = @Value(_lengthmultiplier)
    REPROJECTION_PARAMS = @Value(_reprojection_params)
    Reprojected -> WallSurface (writer CITYGML_2)
WallSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, uro_ifc_boundary_surface_attribute{}.uro_ifc_building_uro_global_id xml_buffer, uro_ifc_boundary_surface_attribute{}.uro_ifc_building_uro_name xml_buffer, uro_ifc_boundary_surface_attribute{}.uro_ifc_building_uro_description xml_buffer, uro_ifc_boundary_surface_attribute{}.uro_ifc_building_uro_object_type xml_buffer, uro_ifc_boundary_surface_attribute{}.uro_ifc_building_uro_long_name xml_buffer, uro_ifc_boundary_surface_attribute{}.uro_ifc_building_uro_composition_type xml_char(7), uro_ifc_boundary_surface_attribute{}.uro_ifc_building_uro_elevation_of_ref_height xml_real64, uro_ifc_boundary_surface_attribute{}.uro_ifc_building_uro_elevation_of_ref_height_units xml_buffer, uro_ifc_boundary_surface_attribute{}.uro_ifc_building_uro_elevation_of_terrain xml_real64, uro_ifc_boundary_surface_attribute{}.uro_ifc_building_uro_elevation_of_terrain_units xml_buffer, uro_ifc_boundary_surface_attribute{}.uro_ifc_building_uro_building_address_xlink_href xml_buffer, uro_ifc_boundary_surface_attribute{}.uro_ifc_building_element_uro_global_id xml_buffer, uro_ifc_boundary_surface_attribute{}.uro_ifc_building_element_uro_name xml_buffer, uro_ifc_boundary_surface_attribute{}.uro_ifc_building_element_uro_description xml_buffer,
      uro_ifc_boundary_surface_attribute{}.uro_ifc_building_element_uro_object_type xml_buffer, uro_ifc_boundary_surface_attribute{}.uro_ifc_building_element_uro_tag xml_buffer, uro_ifc_boundary_surface_attribute{}.uro_ifc_building_element_uro_element_type xml_buffer, uro_ifc_boundary_surface_attribute{}.uro_ifc_building_element_uro_element_type_codeSpace xml_buffer, uro_ifc_boundary_surface_attribute{}.uro_ifc_building_element_uro_predefined_type xml_buffer, uro_ifc_boundary_surface_attribute{}.uro_ifc_building_element_uro_predefined_type_codeSpace xml_buffer, uro_ifc_boundary_surface_attribute{}.uro_ifc_building_element_uro_shape_type xml_buffer, uro_ifc_boundary_surface_attribute{}.uro_ifc_building_element_uro_shape_type_codeSpace xml_buffer, uro_ifc_boundary_surface_attribute{}.uro_ifc_building_element_uro_number_of_riser xml_int64, uro_ifc_boundary_surface_attribute{}.uro_ifc_building_element_uro_number_of_treads xml_int64, uro_ifc_boundary_surface_attribute{}.uro_ifc_building_element_uro_riser_height xml_int64, uro_ifc_boundary_surface_attribute{}.uro_ifc_building_element_uro_tread_length xml_int64, uro_ifc_boundary_surface_attribute{}.uro_ifc_building_element_uro_operation_type xml_char(11), uro_ifc_boundary_surface_attribute{}.uro_ifc_building_element_uro_capacity_by_weight xml_real64, uro_ifc_boundary_surface_attribute{}.uro_ifc_building_element_uro_capacity_by_weight_units xml_buffer, uro_ifc_boundary_surface_attribute{}.uro_ifc_building_element_uro_capacity_by_number xml_int64, uro_ifc_boundary_surface_attribute{}.uro_ifc_building_storey_uro_global_id xml_buffer, uro_ifc_boundary_surface_attribute{}.uro_ifc_building_storey_uro_name xml_buffer, uro_ifc_boundary_surface_attribute{}.uro_ifc_building_storey_uro_description xml_buffer, uro_ifc_boundary_surface_attribute{}.uro_ifc_building_storey_uro_object_type xml_buffer, uro_ifc_boundary_surface_attribute{}.uro_ifc_building_storey_uro_long_name xml_buffer, uro_ifc_boundary_surface_attribute{}.uro_ifc_building_storey_uro_composition_type xml_char(7), uro_ifc_boundary_surface_attribute{}.uro_ifc_building_storey_uro_elevation xml_real64, uro_ifc_boundary_surface_attribute{}.uro_ifc_building_storey_uro_elevation_units xml_buffer, uro_ifc_boundary_surface_attribute{}.uro_ifc_classification_reference_uro_location xml_buffer, uro_ifc_boundary_surface_attribute{}.uro_ifc_classification_reference_uro_item_reference xml_buffer, uro_ifc_boundary_surface_attribute{}.uro_ifc_classification_reference_uro_item_reference_codeSpace xml_buffer, uro_ifc_boundary_surface_attribute{}.uro_ifc_classification_reference_uro_name xml_buffer, uro_ifc_boundary_surface_attribute{}.uro_ifc_classification_reference_uro_name_codeSpace xml_buffer, uro_ifc_boundary_surface_attribute{}.uro_ifc_classification_reference_uro_reference_source_uro_ifc_classification_uro_source xml_buffer,
      uro_ifc_boundary_surface_attribute{}.uro_ifc_classification_reference_uro_reference_source_uro_ifc_classification_uro_edition xml_buffer, uro_ifc_boundary_surface_attribute{}.uro_ifc_classification_reference_uro_reference_source_uro_ifc_classification_uro_edition_date xml_date, uro_ifc_boundary_surface_attribute{}.uro_ifc_classification_reference_uro_reference_source_uro_ifc_classification_uro_name xml_buffer, uro_ifc_boundary_surface_attribute{}.uro_ifc_coordinate_reference_system_uro_name xml_buffer, uro_ifc_boundary_surface_attribute{}.uro_ifc_coordinate_reference_system_uro_description xml_buffer, uro_ifc_boundary_surface_attribute{}.uro_ifc_coordinate_reference_system_uro_geodetic_datum xml_buffer, uro_ifc_boundary_surface_attribute{}.uro_ifc_coordinate_reference_system_uro_vertical_datum xml_buffer, uro_ifc_boundary_surface_attribute{}.uro_ifc_curtain_wall_uro_global_id xml_buffer, uro_ifc_boundary_surface_attribute{}.uro_ifc_curtain_wall_uro_name xml_buffer, uro_ifc_boundary_surface_attribute{}.uro_ifc_curtain_wall_uro_description xml_buffer, uro_ifc_boundary_surface_attribute{}.uro_ifc_curtain_wall_uro_object_type xml_buffer, uro_ifc_boundary_surface_attribute{}.uro_ifc_curtain_wall_uro_tag xml_buffer, uro_ifc_boundary_surface_attribute{}.uro_ifc_curtain_wall_uro_element_type xml_buffer, uro_ifc_boundary_surface_attribute{}.uro_ifc_curtain_wall_uro_element_type_codeSpace xml_buffer, uro_ifc_boundary_surface_attribute{}.uro_ifc_curtain_wall_uro_predefined_type xml_buffer, uro_ifc_boundary_surface_attribute{}.uro_ifc_curtain_wall_uro_predefined_type_codeSpace xml_buffer, uro_ifc_boundary_surface_attribute{}.uro_ifc_curtain_wall_uro_shape_type xml_buffer, uro_ifc_boundary_surface_attribute{}.uro_ifc_curtain_wall_uro_shape_type_codeSpace xml_buffer, uro_ifc_boundary_surface_attribute{}.uro_ifc_curtain_wall_uro_number_of_riser xml_int64, uro_ifc_boundary_surface_attribute{}.uro_ifc_curtain_wall_uro_number_of_treads xml_int64, uro_ifc_boundary_surface_attribute{}.uro_ifc_curtain_wall_uro_riser_height xml_int64, uro_ifc_boundary_surface_attribute{}.uro_ifc_curtain_wall_uro_tread_length xml_int64, uro_ifc_boundary_surface_attribute{}.uro_ifc_curtain_wall_uro_operation_type xml_char(11), uro_ifc_boundary_surface_attribute{}.uro_ifc_curtain_wall_uro_capacity_by_weight xml_real64, uro_ifc_boundary_surface_attribute{}.uro_ifc_curtain_wall_uro_capacity_by_weight_units xml_buffer, uro_ifc_boundary_surface_attribute{}.uro_ifc_curtain_wall_uro_capacity_by_number xml_int64, uro_ifc_boundary_surface_attribute{}.uro_ifc_door_uro_global_id xml_buffer, uro_ifc_boundary_surface_attribute{}.uro_ifc_door_uro_name xml_buffer, uro_ifc_boundary_surface_attribute{}.uro_ifc_door_uro_description xml_buffer, uro_ifc_boundary_surface_attribute{}.uro_ifc_door_uro_object_type xml_buffer,
      uro_ifc_boundary_surface_attribute{}.uro_ifc_door_uro_tag xml_buffer, uro_ifc_boundary_surface_attribute{}.uro_ifc_door_uro_element_type xml_buffer, uro_ifc_boundary_surface_attribute{}.uro_ifc_door_uro_element_type_codeSpace xml_buffer, uro_ifc_boundary_surface_attribute{}.uro_ifc_door_uro_predefined_type xml_buffer, uro_ifc_boundary_surface_attribute{}.uro_ifc_door_uro_predefined_type_codeSpace xml_buffer, uro_ifc_boundary_surface_attribute{}.uro_ifc_door_uro_shape_type xml_buffer, uro_ifc_boundary_surface_attribute{}.uro_ifc_door_uro_shape_type_codeSpace xml_buffer, uro_ifc_boundary_surface_attribute{}.uro_ifc_door_uro_number_of_riser xml_int64, uro_ifc_boundary_surface_attribute{}.uro_ifc_door_uro_number_of_treads xml_int64, uro_ifc_boundary_surface_attribute{}.uro_ifc_door_uro_riser_height xml_int64, uro_ifc_boundary_surface_attribute{}.uro_ifc_door_uro_tread_length xml_int64, uro_ifc_boundary_surface_attribute{}.uro_ifc_door_uro_operation_type xml_char(11), uro_ifc_boundary_surface_attribute{}.uro_ifc_door_uro_capacity_by_weight xml_real64, uro_ifc_boundary_surface_attribute{}.uro_ifc_door_uro_capacity_by_weight_units xml_buffer, uro_ifc_boundary_surface_attribute{}.uro_ifc_door_uro_capacity_by_number xml_int64, uro_ifc_boundary_surface_attribute{}.uro_ifc_door_uro_overall_height xml_real64, uro_ifc_boundary_surface_attribute{}.uro_ifc_door_uro_overall_height_units xml_buffer, uro_ifc_boundary_surface_attribute{}.uro_ifc_door_uro_overall_width xml_real64, uro_ifc_boundary_surface_attribute{}.uro_ifc_door_uro_overall_width_units xml_buffer, uro_ifc_boundary_surface_attribute{}.uro_ifc_furnishing_element_uro_global_id xml_buffer, uro_ifc_boundary_surface_attribute{}.uro_ifc_furnishing_element_uro_name xml_buffer, uro_ifc_boundary_surface_attribute{}.uro_ifc_furnishing_element_uro_description xml_buffer, uro_ifc_boundary_surface_attribute{}.uro_ifc_furnishing_element_uro_object_type xml_buffer, uro_ifc_boundary_surface_attribute{}.uro_ifc_furnishing_element_uro_tag xml_buffer, uro_ifc_boundary_surface_attribute{}.uro_ifc_map_conversion_uro_source_crs_uro_crs_uro_ifc_projected_crs_uro_name xml_buffer, uro_ifc_boundary_surface_attribute{}.uro_ifc_map_conversion_uro_source_crs_uro_crs_uro_ifc_projected_crs_uro_description xml_buffer, uro_ifc_boundary_surface_attribute{}.uro_ifc_map_conversion_uro_source_crs_uro_crs_uro_ifc_projected_crs_uro_geodetic_datum xml_buffer, uro_ifc_boundary_surface_attribute{}.uro_ifc_map_conversion_uro_source_crs_uro_crs_uro_ifc_projected_crs_uro_vertical_datum xml_buffer, uro_ifc_boundary_surface_attribute{}.uro_ifc_map_conversion_uro_source_crs_uro_crs_uro_ifc_projected_crs_uro_map_unit xml_buffer, uro_ifc_boundary_surface_attribute{}.uro_ifc_map_conversion_uro_source_crs_uro_crs_uro_ifc_projected_crs_uro_map_projection xml_buffer,
      uro_ifc_boundary_surface_attribute{}.uro_ifc_map_conversion_uro_source_crs_uro_crs_uro_ifc_projected_crs_uro_map_zone xml_buffer, uro_ifc_boundary_surface_attribute{}.uro_ifc_map_conversion_uro_source_crs_uro_crs_uro_ifc_coordinate_reference_system_uro_name xml_buffer, uro_ifc_boundary_surface_attribute{}.uro_ifc_map_conversion_uro_source_crs_uro_crs_uro_ifc_coordinate_reference_system_uro_description xml_buffer, uro_ifc_boundary_surface_attribute{}.uro_ifc_map_conversion_uro_source_crs_uro_crs_uro_ifc_coordinate_reference_system_uro_geodetic_datum xml_buffer, uro_ifc_boundary_surface_attribute{}.uro_ifc_map_conversion_uro_source_crs_uro_crs_uro_ifc_coordinate_reference_system_uro_vertical_datum xml_buffer, uro_ifc_boundary_surface_attribute{}.uro_ifc_map_conversion_uro_source_crs_uro_context_uro_ifc_geometric_representation_context_uro_context_identifier xml_buffer, uro_ifc_boundary_surface_attribute{}.uro_ifc_map_conversion_uro_source_crs_uro_context_uro_ifc_geometric_representation_context_uro_context_type xml_buffer, uro_ifc_boundary_surface_attribute{}.uro_ifc_map_conversion_uro_source_crs_uro_context_uro_ifc_geometric_representation_context_uro_coordinate_space_dimension xml_int64, uro_ifc_boundary_surface_attribute{}.uro_ifc_map_conversion_uro_source_crs_uro_context_uro_ifc_geometric_representation_context_uro_precision xml_real64, uro_ifc_boundary_surface_attribute{}.uro_ifc_map_conversion_uro_source_crs_uro_context_uro_ifc_geometric_representation_context_uro_true_north xml_real64, uro_ifc_boundary_surface_attribute{}.uro_ifc_map_conversion_uro_target_crs_uro_ifc_projected_crs_uro_name xml_buffer, uro_ifc_boundary_surface_attribute{}.uro_ifc_map_conversion_uro_target_crs_uro_ifc_projected_crs_uro_description xml_buffer, uro_ifc_boundary_surface_attribute{}.uro_ifc_map_conversion_uro_target_crs_uro_ifc_projected_crs_uro_geodetic_datum xml_buffer, uro_ifc_boundary_surface_attribute{}.uro_ifc_map_conversion_uro_target_crs_uro_ifc_projected_crs_uro_vertical_datum xml_buffer, uro_ifc_boundary_surface_attribute{}.uro_ifc_map_conversion_uro_target_crs_uro_ifc_projected_crs_uro_map_unit xml_buffer, uro_ifc_boundary_surface_attribute{}.uro_ifc_map_conversion_uro_target_crs_uro_ifc_projected_crs_uro_map_projection xml_buffer, uro_ifc_boundary_surface_attribute{}.uro_ifc_map_conversion_uro_target_crs_uro_ifc_projected_crs_uro_map_zone xml_buffer, uro_ifc_boundary_surface_attribute{}.uro_ifc_map_conversion_uro_target_crs_uro_ifc_coordinate_reference_system_uro_name xml_buffer, uro_ifc_boundary_surface_attribute{}.uro_ifc_map_conversion_uro_target_crs_uro_ifc_coordinate_reference_system_uro_description xml_buffer, uro_ifc_boundary_surface_attribute{}.uro_ifc_map_conversion_uro_target_crs_uro_ifc_coordinate_reference_system_uro_geodetic_datum xml_buffer, uro_ifc_boundary_surface_attribute{}.uro_ifc_map_conversion_uro_target_crs_uro_ifc_coordinate_reference_system_uro_vertical_datum xml_buffer, uro_ifc_boundary_surface_attribute{}.uro_ifc_map_conversion_uro_eastings xml_buffer, uro_ifc_boundary_surface_attribute{}.uro_ifc_map_conversion_uro_northings xml_buffer, uro_ifc_boundary_surface_attribute{}.uro_ifc_map_conversion_uro_orthogonal_height xml_real64, uro_ifc_boundary_surface_attribute{}.uro_ifc_map_conversion_uro_orthogonal_height_units xml_buffer, uro_ifc_boundary_surface_attribute{}.uro_ifc_map_conversion_uro_x_axis_abscissa xml_real64, uro_ifc_boundary_surface_attribute{}.uro_ifc_map_conversion_uro_x_axis_ordinate xml_real64, uro_ifc_boundary_surface_attribute{}.uro_ifc_map_conversion_uro_scale xml_real64, uro_ifc_boundary_surface_attribute{}.uro_ifc_opening_element_uro_global_id xml_buffer, uro_ifc_boundary_surface_attribute{}.uro_ifc_opening_element_uro_name xml_buffer,
      uro_ifc_boundary_surface_attribute{}.uro_ifc_opening_element_uro_description xml_buffer, uro_ifc_boundary_surface_attribute{}.uro_ifc_opening_element_uro_object_type xml_buffer, uro_ifc_boundary_surface_attribute{}.uro_ifc_opening_element_uro_tag xml_buffer, uro_ifc_boundary_surface_attribute{}.uro_ifc_opening_element_uro_nominal_area xml_real64, uro_ifc_boundary_surface_attribute{}.uro_ifc_opening_element_uro_nominal_area_units xml_buffer, uro_ifc_boundary_surface_attribute{}.uro_ifc_opening_element_uro_nominal_volume xml_real64, uro_ifc_boundary_surface_attribute{}.uro_ifc_opening_element_uro_nominal_volume_units xml_buffer, uro_ifc_boundary_surface_attribute{}.uro_ifc_project_uro_global_id xml_buffer, uro_ifc_boundary_surface_attribute{}.uro_ifc_project_uro_name xml_buffer, uro_ifc_boundary_surface_attribute{}.uro_ifc_project_uro_description xml_buffer, uro_ifc_boundary_surface_attribute{}.uro_ifc_project_uro_object_type xml_buffer, uro_ifc_boundary_surface_attribute{}.uro_ifc_project_uro_long_name xml_buffer, uro_ifc_boundary_surface_attribute{}.uro_ifc_project_uro_phase xml_buffer, uro_ifc_boundary_surface_attribute{}.uro_ifc_project_uro_representation_contexts_uro_ifc_geometric_representation_context_uro_context_identifier xml_buffer, uro_ifc_boundary_surface_attribute{}.uro_ifc_project_uro_representation_contexts_uro_ifc_geometric_representation_context_uro_context_type xml_buffer, uro_ifc_boundary_surface_attribute{}.uro_ifc_project_uro_representation_contexts_uro_ifc_geometric_representation_context_uro_coordinate_space_dimension xml_int64, uro_ifc_boundary_surface_attribute{}.uro_ifc_project_uro_representation_contexts_uro_ifc_geometric_representation_context_uro_precision xml_real64, uro_ifc_boundary_surface_attribute{}.uro_ifc_project_uro_representation_contexts_uro_ifc_geometric_representation_context_uro_true_north xml_real64, uro_ifc_boundary_surface_attribute{}.uro_ifc_project_uro_units_in_context{}.uro_ifc_unit_uro_dimensions xml_int64, uro_ifc_boundary_surface_attribute{}.uro_ifc_project_uro_units_in_context{}.uro_ifc_unit_uro_unit_type xml_char(28), uro_ifc_boundary_surface_attribute{}.uro_ifc_project_uro_units_in_context{}.uro_ifc_unit_uro_perfix xml_buffer, uro_ifc_boundary_surface_attribute{}.uro_ifc_project_uro_units_in_context{}.uro_ifc_unit_uro_name xml_buffer, uro_ifc_boundary_surface_attribute{}.uro_ifc_projected_crs_uro_name xml_buffer, uro_ifc_boundary_surface_attribute{}.uro_ifc_projected_crs_uro_description xml_buffer, uro_ifc_boundary_surface_attribute{}.uro_ifc_projected_crs_uro_geodetic_datum xml_buffer, uro_ifc_boundary_surface_attribute{}.uro_ifc_projected_crs_uro_vertical_datum xml_buffer, uro_ifc_boundary_surface_attribute{}.uro_ifc_projected_crs_uro_map_unit xml_buffer, uro_ifc_boundary_surface_attribute{}.uro_ifc_projected_crs_uro_map_projection xml_buffer, uro_ifc_boundary_surface_attribute{}.uro_ifc_projected_crs_uro_map_zone xml_buffer, uro_ifc_boundary_surface_attribute{}.uro_ifc_pset_building_common_uro_building_id xml_real64,
      uro_ifc_boundary_surface_attribute{}.uro_ifc_pset_building_common_uro_building_id_units xml_buffer, uro_ifc_boundary_surface_attribute{}.uro_ifc_pset_building_common_uro_is_permanent_id xml_real64, uro_ifc_boundary_surface_attribute{}.uro_ifc_pset_building_common_uro_is_permanent_id_units xml_buffer, uro_ifc_boundary_surface_attribute{}.uro_ifc_pset_building_common_uro_main_fire_use xml_buffer, uro_ifc_boundary_surface_attribute{}.uro_ifc_pset_building_common_uro_ancillary_fire_use xml_buffer, uro_ifc_boundary_surface_attribute{}.uro_ifc_pset_building_common_uro_sprinkler_protection xml_boolean, uro_ifc_boundary_surface_attribute{}.uro_ifc_pset_building_common_uro_sprinkler_protection_automatic xml_boolean, uro_ifc_boundary_surface_attribute{}.uro_ifc_pset_building_common_uro_occupancy_type xml_buffer, uro_ifc_boundary_surface_attribute{}.uro_ifc_pset_building_common_uro_occupancy_type_codeSpace xml_buffer, uro_ifc_boundary_surface_attribute{}.uro_ifc_pset_building_common_uro_gross_planned_area xml_real64, uro_ifc_boundary_surface_attribute{}.uro_ifc_pset_building_common_uro_gross_planned_area_units xml_buffer, uro_ifc_boundary_surface_attribute{}.uro_ifc_pset_building_common_uro_number_of_storeys xml_int64, uro_ifc_boundary_surface_attribute{}.uro_ifc_pset_building_common_uro_year_of_construction xml_buffer, uro_ifc_boundary_surface_attribute{}.uro_ifc_pset_building_common_uro_is_landmarked xml_boolean, uro_ifc_boundary_surface_attribute{}.uro_ifc_pset_door_common_uro_reference xml_buffer, uro_ifc_boundary_surface_attribute{}.uro_ifc_pset_door_common_uro_acoustic_rating xml_buffer, uro_ifc_boundary_surface_attribute{}.uro_ifc_pset_door_common_uro_firerating xml_buffer, uro_ifc_boundary_surface_attribute{}.uro_ifc_pset_door_common_uro_security_rating xml_buffer, uro_ifc_boundary_surface_attribute{}.uro_ifc_pset_door_common_uro_is_external xml_boolean, uro_ifc_boundary_surface_attribute{}.uro_ifc_pset_door_common_uro_infiltration xml_real64, uro_ifc_boundary_surface_attribute{}.uro_ifc_pset_door_common_uro_thermal_transmittance xml_real64, uro_ifc_boundary_surface_attribute{}.uro_ifc_pset_door_common_uro_glazing_area_fraction xml_real64, uro_ifc_boundary_surface_attribute{}.uro_ifc_pset_door_common_uro_handicap_accessible xml_real64, uro_ifc_boundary_surface_attribute{}.uro_ifc_pset_door_common_uro_fire_exit xml_boolean, uro_ifc_boundary_surface_attribute{}.uro_ifc_pset_door_common_uro_self_closing xml_real64, uro_ifc_boundary_surface_attribute{}.uro_ifc_pset_door_common_uro_smoke_stop xml_boolean, uro_ifc_boundary_surface_attribute{}.uro_ifc_pset_opening_element_common_uro_reference xml_buffer, uro_ifc_boundary_surface_attribute{}.uro_ifc_pset_opening_element_common_uro_purpose xml_buffer, uro_ifc_boundary_surface_attribute{}.uro_ifc_pset_opening_element_common_uro_fire_exit xml_boolean, uro_ifc_boundary_surface_attribute{}.uro_ifc_pset_opening_element_common_uro_protected_opening xml_boolean,
      uro_ifc_boundary_surface_attribute{}.uro_ifc_pset_opening_element_common_uro_parallel_jambs xml_boolean, uro_ifc_boundary_surface_attribute{}.uro_ifc_pset_site_common_uro_buildable_area xml_real64, uro_ifc_boundary_surface_attribute{}.uro_ifc_pset_site_common_uro_buildable_area_units xml_buffer, uro_ifc_boundary_surface_attribute{}.uro_ifc_pset_site_common_uro_total_area xml_real64, uro_ifc_boundary_surface_attribute{}.uro_ifc_pset_site_common_uro_total_area_units xml_buffer, uro_ifc_boundary_surface_attribute{}.uro_ifc_pset_site_common_uro_building_height_limit xml_real64, uro_ifc_boundary_surface_attribute{}.uro_ifc_pset_site_common_uro_building_height_limit_units xml_buffer, uro_ifc_boundary_surface_attribute{}.uro_ifc_pset_space_common_uro_reference xml_buffer, uro_ifc_boundary_surface_attribute{}.uro_ifc_pset_space_common_uro_category xml_buffer, uro_ifc_boundary_surface_attribute{}.uro_ifc_pset_space_common_uro_category_codeSpace xml_buffer, uro_ifc_boundary_surface_attribute{}.uro_ifc_pset_space_common_uro_floor_covering xml_buffer, uro_ifc_boundary_surface_attribute{}.uro_ifc_pset_space_common_uro_wall_covering xml_buffer, uro_ifc_boundary_surface_attribute{}.uro_ifc_pset_space_common_uro_ceiling_covering xml_buffer, uro_ifc_boundary_surface_attribute{}.uro_ifc_pset_space_common_uro_skirting_covering xml_buffer, uro_ifc_boundary_surface_attribute{}.uro_ifc_pset_space_common_uro_gross_planned_area xml_real64, uro_ifc_boundary_surface_attribute{}.uro_ifc_pset_space_common_uro_gross_planned_area_units xml_buffer, uro_ifc_boundary_surface_attribute{}.uro_ifc_pset_space_common_uro_net_planned_area xml_real64, uro_ifc_boundary_surface_attribute{}.uro_ifc_pset_space_common_uro_net_planned_area_units xml_buffer, uro_ifc_boundary_surface_attribute{}.uro_ifc_pset_space_common_uro_publicly_accessible xml_boolean, uro_ifc_boundary_surface_attribute{}.uro_ifc_pset_space_common_uro_handicap_accessible xml_boolean, uro_ifc_boundary_surface_attribute{}.uro_ifc_pset_space_common_uro_concealed_flooring xml_boolean, uro_ifc_boundary_surface_attribute{}.uro_ifc_pset_space_common_uro_concealed_ceiling xml_boolean, uro_ifc_boundary_surface_attribute{}.uro_ifc_pset_window_common_uro_reference xml_buffer, uro_ifc_boundary_surface_attribute{}.uro_ifc_pset_window_common_uro_acoustic_rating xml_buffer, uro_ifc_boundary_surface_attribute{}.uro_ifc_pset_window_common_uro_firerating xml_buffer, uro_ifc_boundary_surface_attribute{}.uro_ifc_pset_window_common_uro_security_rating xml_buffer, uro_ifc_boundary_surface_attribute{}.uro_ifc_pset_window_common_uro_is_external xml_boolean, uro_ifc_boundary_surface_attribute{}.uro_ifc_pset_window_common_uro_infiltration xml_real64, uro_ifc_boundary_surface_attribute{}.uro_ifc_pset_window_common_uro_thermal_transmittance xml_real64, uro_ifc_boundary_surface_attribute{}.uro_ifc_pset_window_common_uro_glazing_area_fraction xml_real64,
      uro_ifc_boundary_surface_attribute{}.uro_ifc_pset_window_common_uro_smoke_stop xml_boolean, uro_ifc_boundary_surface_attribute{}.uro_ifc_site_uro_global_id xml_buffer, uro_ifc_boundary_surface_attribute{}.uro_ifc_site_uro_name xml_buffer, uro_ifc_boundary_surface_attribute{}.uro_ifc_site_uro_description xml_buffer, uro_ifc_boundary_surface_attribute{}.uro_ifc_site_uro_object_type xml_buffer, uro_ifc_boundary_surface_attribute{}.uro_ifc_site_uro_long_name xml_buffer, uro_ifc_boundary_surface_attribute{}.uro_ifc_site_uro_composition_type xml_char(7), uro_ifc_boundary_surface_attribute{}.uro_ifc_site_uro_ref_longitude xml_real64, uro_ifc_boundary_surface_attribute{}.uro_ifc_site_uro_ref_latitude xml_real64, uro_ifc_boundary_surface_attribute{}.uro_ifc_site_uro_ref_elevation xml_real64, uro_ifc_boundary_surface_attribute{}.uro_ifc_site_uro_ref_elevation_units xml_buffer, uro_ifc_boundary_surface_attribute{}.uro_ifc_site_uro_land_title_number xml_buffer, uro_ifc_boundary_surface_attribute{}.uro_ifc_site_uro_site_address_xlink_href xml_buffer, uro_ifc_boundary_surface_attribute{}.uro_ifc_space_uro_global_id xml_buffer, uro_ifc_boundary_surface_attribute{}.uro_ifc_space_uro_name xml_buffer, uro_ifc_boundary_surface_attribute{}.uro_ifc_space_uro_description xml_buffer, uro_ifc_boundary_surface_attribute{}.uro_ifc_space_uro_object_type xml_buffer, uro_ifc_boundary_surface_attribute{}.uro_ifc_space_uro_long_name xml_buffer, uro_ifc_boundary_surface_attribute{}.uro_ifc_space_uro_composition_type xml_char(7), uro_ifc_boundary_surface_attribute{}.uro_ifc_space_uro_interioror_exterior_space xml_char(10), uro_ifc_boundary_surface_attribute{}.uro_ifc_space_uro_elevation_with_flooring xml_real64, uro_ifc_boundary_surface_attribute{}.uro_ifc_space_uro_elevation_with_flooring_units xml_buffer, uro_ifc_boundary_surface_attribute{}.uro_ifc_space_base_quantity_uro_nominal_height xml_real64, uro_ifc_boundary_surface_attribute{}.uro_ifc_space_base_quantity_uro_nominal_height_units xml_buffer, uro_ifc_boundary_surface_attribute{}.uro_ifc_space_base_quantity_uro_clear_height xml_real64, uro_ifc_boundary_surface_attribute{}.uro_ifc_space_base_quantity_uro_clear_height_units xml_buffer, uro_ifc_boundary_surface_attribute{}.uro_ifc_space_base_quantity_uro_finish_ceiling_height xml_real64, uro_ifc_boundary_surface_attribute{}.uro_ifc_space_base_quantity_uro_finish_ceiling_height_units xml_buffer, uro_ifc_boundary_surface_attribute{}.uro_ifc_space_base_quantity_uro_gross_perimeter xml_real64, uro_ifc_boundary_surface_attribute{}.uro_ifc_space_base_quantity_uro_gross_perimeter_units xml_buffer,
      uro_ifc_boundary_surface_attribute{}.uro_ifc_space_base_quantity_uro_net_perimeter xml_real64, uro_ifc_boundary_surface_attribute{}.uro_ifc_space_base_quantity_uro_net_perimeter_units xml_buffer, uro_ifc_boundary_surface_attribute{}.uro_ifc_space_base_quantity_uro_gross_ceiling_area xml_real64, uro_ifc_boundary_surface_attribute{}.uro_ifc_space_base_quantity_uro_gross_ceiling_area_units xml_buffer, uro_ifc_boundary_surface_attribute{}.uro_ifc_space_base_quantity_uro_gross_floor_area xml_real64, uro_ifc_boundary_surface_attribute{}.uro_ifc_space_base_quantity_uro_gross_floor_area_units xml_buffer, uro_ifc_boundary_surface_attribute{}.uro_ifc_space_base_quantity_uro_net_ceiling_area xml_real64, uro_ifc_boundary_surface_attribute{}.uro_ifc_space_base_quantity_uro_net_ceiling_area_units xml_buffer, uro_ifc_boundary_surface_attribute{}.uro_ifc_space_base_quantity_uro_net_floor_area xml_real64, uro_ifc_boundary_surface_attribute{}.uro_ifc_space_base_quantity_uro_net_floor_area_units xml_buffer, uro_ifc_boundary_surface_attribute{}.uro_ifc_space_base_quantity_uro_gross_wall_area xml_real64, uro_ifc_boundary_surface_attribute{}.uro_ifc_space_base_quantity_uro_gross_wall_area_units xml_buffer, uro_ifc_boundary_surface_attribute{}.uro_ifc_space_base_quantity_uro_net_wall_area xml_real64, uro_ifc_boundary_surface_attribute{}.uro_ifc_space_base_quantity_uro_net_wall_area_units xml_buffer, uro_ifc_boundary_surface_attribute{}.uro_ifc_space_base_quantity_uro_gross_volume xml_real64, uro_ifc_boundary_surface_attribute{}.uro_ifc_space_base_quantity_uro_gross_volume_units xml_buffer, uro_ifc_boundary_surface_attribute{}.uro_ifc_space_base_quantity_uro_net_volume xml_real64, uro_ifc_boundary_surface_attribute{}.uro_ifc_space_base_quantity_uro_net_volume_units xml_buffer, uro_ifc_boundary_surface_attribute{}.uro_ifc_wall_uro_global_id xml_buffer, uro_ifc_boundary_surface_attribute{}.uro_ifc_wall_uro_name xml_buffer, uro_ifc_boundary_surface_attribute{}.uro_ifc_wall_uro_description xml_buffer, uro_ifc_boundary_surface_attribute{}.uro_ifc_wall_uro_object_type xml_buffer, uro_ifc_boundary_surface_attribute{}.uro_ifc_wall_uro_tag xml_buffer, uro_ifc_boundary_surface_attribute{}.uro_ifc_wall_uro_element_type xml_buffer, uro_ifc_boundary_surface_attribute{}.uro_ifc_wall_uro_element_type_codeSpace xml_buffer, uro_ifc_boundary_surface_attribute{}.uro_ifc_wall_uro_predefined_type xml_buffer, uro_ifc_boundary_surface_attribute{}.uro_ifc_wall_uro_predefined_type_codeSpace xml_buffer, uro_ifc_boundary_surface_attribute{}.uro_ifc_wall_uro_shape_type xml_buffer, uro_ifc_boundary_surface_attribute{}.uro_ifc_wall_uro_shape_type_codeSpace xml_buffer, uro_ifc_boundary_surface_attribute{}.uro_ifc_wall_uro_number_of_riser xml_int64,
      uro_ifc_boundary_surface_attribute{}.uro_ifc_wall_uro_number_of_treads xml_int64, uro_ifc_boundary_surface_attribute{}.uro_ifc_wall_uro_riser_height xml_int64, uro_ifc_boundary_surface_attribute{}.uro_ifc_wall_uro_tread_length xml_int64, uro_ifc_boundary_surface_attribute{}.uro_ifc_wall_uro_operation_type xml_char(11), uro_ifc_boundary_surface_attribute{}.uro_ifc_wall_uro_capacity_by_weight xml_real64, uro_ifc_boundary_surface_attribute{}.uro_ifc_wall_uro_capacity_by_weight_units xml_buffer, uro_ifc_boundary_surface_attribute{}.uro_ifc_wall_uro_capacity_by_number xml_int64, uro_ifc_boundary_surface_attribute{}.uro_ifc_wall_uro_nominal_length xml_real64, uro_ifc_boundary_surface_attribute{}.uro_ifc_wall_uro_nominal_length_units xml_buffer, uro_ifc_boundary_surface_attribute{}.uro_ifc_wall_uro_nominal_width xml_real64, uro_ifc_boundary_surface_attribute{}.uro_ifc_wall_uro_nominal_width_units xml_buffer, uro_ifc_boundary_surface_attribute{}.uro_ifc_wall_uro_nominal_height xml_real64, uro_ifc_boundary_surface_attribute{}.uro_ifc_wall_uro_nominal_height_units xml_buffer, uro_ifc_boundary_surface_attribute{}.uro_ifc_wall_uro_gross_foot_print_area xml_real64, uro_ifc_boundary_surface_attribute{}.uro_ifc_wall_uro_gross_foot_print_area_units xml_buffer, uro_ifc_boundary_surface_attribute{}.uro_ifc_wall_uro_net_foot_print_area xml_real64, uro_ifc_boundary_surface_attribute{}.uro_ifc_wall_uro_net_foot_print_area_units xml_buffer, uro_ifc_boundary_surface_attribute{}.uro_ifc_wall_uro_gross_side_area xml_real64, uro_ifc_boundary_surface_attribute{}.uro_ifc_wall_uro_gross_side_area_units xml_buffer, uro_ifc_boundary_surface_attribute{}.uro_ifc_wall_uro_net_side_area xml_real64, uro_ifc_boundary_surface_attribute{}.uro_ifc_wall_uro_net_side_area_units xml_buffer, uro_ifc_boundary_surface_attribute{}.uro_ifc_wall_uro_gross_side_area_left xml_real64, uro_ifc_boundary_surface_attribute{}.uro_ifc_wall_uro_gross_side_area_left_units xml_buffer, uro_ifc_boundary_surface_attribute{}.uro_ifc_wall_uro_net_side_area_left xml_real64, uro_ifc_boundary_surface_attribute{}.uro_ifc_wall_uro_net_side_area_left_units xml_buffer, uro_ifc_boundary_surface_attribute{}.uro_ifc_wall_uro_gross_side_area_right xml_real64, uro_ifc_boundary_surface_attribute{}.uro_ifc_wall_uro_gross_side_area_right_units xml_buffer, uro_ifc_boundary_surface_attribute{}.uro_ifc_wall_uro_net_side_area_right xml_real64, uro_ifc_boundary_surface_attribute{}.uro_ifc_wall_uro_net_side_area_right_units xml_buffer, uro_ifc_boundary_surface_attribute{}.uro_ifc_wall_uro_gross_volume xml_real64,
      uro_ifc_boundary_surface_attribute{}.uro_ifc_wall_uro_gross_volume_units xml_buffer, uro_ifc_boundary_surface_attribute{}.uro_ifc_wall_uro_net_volume xml_real64, uro_ifc_boundary_surface_attribute{}.uro_ifc_wall_uro_net_volume_units xml_buffer, uro_ifc_boundary_surface_attribute{}.uro_ifc_wall_standard_case_uro_global_id xml_buffer, uro_ifc_boundary_surface_attribute{}.uro_ifc_wall_standard_case_uro_name xml_buffer, uro_ifc_boundary_surface_attribute{}.uro_ifc_wall_standard_case_uro_description xml_buffer, uro_ifc_boundary_surface_attribute{}.uro_ifc_wall_standard_case_uro_object_type xml_buffer, uro_ifc_boundary_surface_attribute{}.uro_ifc_wall_standard_case_uro_tag xml_buffer, uro_ifc_boundary_surface_attribute{}.uro_ifc_wall_standard_case_uro_element_type xml_buffer, uro_ifc_boundary_surface_attribute{}.uro_ifc_wall_standard_case_uro_element_type_codeSpace xml_buffer, uro_ifc_boundary_surface_attribute{}.uro_ifc_wall_standard_case_uro_predefined_type xml_buffer, uro_ifc_boundary_surface_attribute{}.uro_ifc_wall_standard_case_uro_predefined_type_codeSpace xml_buffer, uro_ifc_boundary_surface_attribute{}.uro_ifc_wall_standard_case_uro_shape_type xml_buffer, uro_ifc_boundary_surface_attribute{}.uro_ifc_wall_standard_case_uro_shape_type_codeSpace xml_buffer, uro_ifc_boundary_surface_attribute{}.uro_ifc_wall_standard_case_uro_number_of_riser xml_int64, uro_ifc_boundary_surface_attribute{}.uro_ifc_wall_standard_case_uro_number_of_treads xml_int64, uro_ifc_boundary_surface_attribute{}.uro_ifc_wall_standard_case_uro_riser_height xml_int64, uro_ifc_boundary_surface_attribute{}.uro_ifc_wall_standard_case_uro_tread_length xml_int64, uro_ifc_boundary_surface_attribute{}.uro_ifc_wall_standard_case_uro_operation_type xml_char(11), uro_ifc_boundary_surface_attribute{}.uro_ifc_wall_standard_case_uro_capacity_by_weight xml_real64, uro_ifc_boundary_surface_attribute{}.uro_ifc_wall_standard_case_uro_capacity_by_weight_units xml_buffer, uro_ifc_boundary_surface_attribute{}.uro_ifc_wall_standard_case_uro_capacity_by_number xml_int64, uro_ifc_boundary_surface_attribute{}.uro_ifc_wall_standard_case_uro_nominal_length xml_real64, uro_ifc_boundary_surface_attribute{}.uro_ifc_wall_standard_case_uro_nominal_length_units xml_buffer, uro_ifc_boundary_surface_attribute{}.uro_ifc_wall_standard_case_uro_nominal_width xml_real64, uro_ifc_boundary_surface_attribute{}.uro_ifc_wall_standard_case_uro_nominal_width_units xml_buffer, uro_ifc_boundary_surface_attribute{}.uro_ifc_wall_standard_case_uro_nominal_height xml_real64, uro_ifc_boundary_surface_attribute{}.uro_ifc_wall_standard_case_uro_nominal_height_units xml_buffer, uro_ifc_boundary_surface_attribute{}.uro_ifc_wall_standard_case_uro_gross_foot_print_area xml_real64, uro_ifc_boundary_surface_attribute{}.uro_ifc_wall_standard_case_uro_gross_foot_print_area_units xml_buffer,
      uro_ifc_boundary_surface_attribute{}.uro_ifc_wall_standard_case_uro_net_foot_print_area xml_real64, uro_ifc_boundary_surface_attribute{}.uro_ifc_wall_standard_case_uro_net_foot_print_area_units xml_buffer, uro_ifc_boundary_surface_attribute{}.uro_ifc_wall_standard_case_uro_gross_side_area xml_real64, uro_ifc_boundary_surface_attribute{}.uro_ifc_wall_standard_case_uro_gross_side_area_units xml_buffer, uro_ifc_boundary_surface_attribute{}.uro_ifc_wall_standard_case_uro_net_side_area xml_real64, uro_ifc_boundary_surface_attribute{}.uro_ifc_wall_standard_case_uro_net_side_area_units xml_buffer, uro_ifc_boundary_surface_attribute{}.uro_ifc_wall_standard_case_uro_gross_side_area_left xml_real64, uro_ifc_boundary_surface_attribute{}.uro_ifc_wall_standard_case_uro_gross_side_area_left_units xml_buffer, uro_ifc_boundary_surface_attribute{}.uro_ifc_wall_standard_case_uro_net_side_area_left xml_real64, uro_ifc_boundary_surface_attribute{}.uro_ifc_wall_standard_case_uro_net_side_area_left_units xml_buffer, uro_ifc_boundary_surface_attribute{}.uro_ifc_wall_standard_case_uro_gross_side_area_right xml_real64, uro_ifc_boundary_surface_attribute{}.uro_ifc_wall_standard_case_uro_gross_side_area_right_units xml_buffer, uro_ifc_boundary_surface_attribute{}.uro_ifc_wall_standard_case_uro_net_side_area_right xml_real64, uro_ifc_boundary_surface_attribute{}.uro_ifc_wall_standard_case_uro_net_side_area_right_units xml_buffer, uro_ifc_boundary_surface_attribute{}.uro_ifc_wall_standard_case_uro_gross_volume xml_real64, uro_ifc_boundary_surface_attribute{}.uro_ifc_wall_standard_case_uro_gross_volume_units xml_buffer, uro_ifc_boundary_surface_attribute{}.uro_ifc_wall_standard_case_uro_net_volume xml_real64, uro_ifc_boundary_surface_attribute{}.uro_ifc_wall_standard_case_uro_net_volume_units xml_buffer, uro_ifc_boundary_surface_attribute{}.uro_ifc_window_uro_global_id xml_buffer, uro_ifc_boundary_surface_attribute{}.uro_ifc_window_uro_name xml_buffer, uro_ifc_boundary_surface_attribute{}.uro_ifc_window_uro_description xml_buffer, uro_ifc_boundary_surface_attribute{}.uro_ifc_window_uro_object_type xml_buffer, uro_ifc_boundary_surface_attribute{}.uro_ifc_window_uro_tag xml_buffer, uro_ifc_boundary_surface_attribute{}.uro_ifc_window_uro_element_type xml_buffer, uro_ifc_boundary_surface_attribute{}.uro_ifc_window_uro_element_type_codeSpace xml_buffer, uro_ifc_boundary_surface_attribute{}.uro_ifc_window_uro_predefined_type xml_buffer, uro_ifc_boundary_surface_attribute{}.uro_ifc_window_uro_predefined_type_codeSpace xml_buffer, uro_ifc_boundary_surface_attribute{}.uro_ifc_window_uro_shape_type xml_buffer, uro_ifc_boundary_surface_attribute{}.uro_ifc_window_uro_shape_type_codeSpace xml_buffer, uro_ifc_boundary_surface_attribute{}.uro_ifc_window_uro_number_of_riser xml_int64,
      uro_ifc_boundary_surface_attribute{}.uro_ifc_window_uro_number_of_treads xml_int64, uro_ifc_boundary_surface_attribute{}.uro_ifc_window_uro_riser_height xml_int64, uro_ifc_boundary_surface_attribute{}.uro_ifc_window_uro_tread_length xml_int64, uro_ifc_boundary_surface_attribute{}.uro_ifc_window_uro_operation_type xml_char(11), uro_ifc_boundary_surface_attribute{}.uro_ifc_window_uro_capacity_by_weight xml_real64, uro_ifc_boundary_surface_attribute{}.uro_ifc_window_uro_capacity_by_weight_units xml_buffer, uro_ifc_boundary_surface_attribute{}.uro_ifc_window_uro_capacity_by_number xml_int64, uro_ifc_boundary_surface_attribute{}.uro_ifc_window_uro_overall_height xml_real64, uro_ifc_boundary_surface_attribute{}.uro_ifc_window_uro_overall_height_units xml_buffer, uro_ifc_boundary_surface_attribute{}.uro_ifc_window_uro_overall_width xml_real64, uro_ifc_boundary_surface_attribute{}.uro_ifc_window_uro_overall_width_units xml_buffer
w8: Inspector [off]
    TACKATTRS = _storey_id
w7: Inspector [off]
    TACKATTRS = _storey_id
Note: 屋外スラブ課題解消のため、このClipperをstoreyでグループ化した。
w6: Inspector [off]
    TACKATTRS = _storey_id
Note: SpatialFilter_5 : Filter
Junction_41
    -> Junction_42
Note: 階ごとに融合した屋内空間フットプリント / Bufferer_5 : Buffered
Junction_42
    -> SpatialFilter_5 [Filter]
Note: _room_gml_id 設定 / Room の gml:id
AttributeManager_4
    ATTR_TABLE:
      RENAME_SET_VALUE ifc_unique_id > _room_ifc_unique_id
      REMOVE Name
      REMOVE ifc_parent_unique_id
      REMOVE _part_number
      REMOVE _geometry_name
      SET_TO _room_gml_id = room_@UUID()
      RENAME_SET_VALUE gml_description > _room_gml_description
      RENAME_SET_VALUE gml_name > _room_gml_name
    -> GeometryPartExtractor_3
Note: _boundary_gml_id / 境界面の gml_id 設定
AttributeCreator
    ATTR_TABLE = SET_TO _boundary_gml_id = bdry_@UUID()
    -> Clipper_2 [CANDIDATE]
Note: 開口部とその他に分割
Clipper_2
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    GROUP_BY = _storey_id
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Tester_10
    OUTSIDE -> TestFilter_4
Note: Door または Window / と / ClosureSurface / に分岐
Tester_10
    BOOL_OP = OR
    TEST_CLAUSE = TEST @Value(_opening_ifc_feature_type) IN IfcDoor,IfcWindow
    TEST_MODE = TEST
    PASSED -> AttributeValueMapper_2
    FAILED -> Junction_79
AttributeValueMapper_2
    LUT = IfcDoor,Door,IfcWindow,Window
    MAPPING_DIRECTION = FORWARD
    SRC = _opening_ifc_feature_type
    VAL_ATTR = fme_feature_type
    -> AttributeManager_11
Note: 屋内開口部: Door, Window
AttributeManager_11
    ATTR_TABLE:
      SET_TO gml_id = FME_CONDITIONAL:DEFAULT_VALUE'wnd_@UUID()'BOOL_OP;OR;COMPOSITE_TEST;1;TEST @Value(fme_feature_type) = Door'door_@UUID()'FME_NUM_CONDITIONS2___
      RENAME_SET_VALUE _boundary_gml_id > gml_parent_id
      RENAME_SET_VALUE _room_gml_id
      RENAME_SET_VALUE _opening_ifc_unique_id > ifc_unique_id
      REMOVE _parent_feature_type
      SET_TO citygml_lod_name = lod4MultiSurface
      SET_TO citygml_feature_role = opening
      REMOVE _ifc_feature_type
      REMOVE _surfaceNormalX
      REMOVE _surfaceNormalY
      REMOVE _surfaceNormalZ
      REMOVE _pointOnSurfaceX
      REMOVE _pointOnSurfaceY
      REMOVE _pointOnSurfaceZ
      REMOVE _clipped
    USER_EXPOSED_ATTRIBUTES = gml_parent_id,_side
    -> Junction_24
    -> Junction_9
Note: FeatureTypeFilter_4 : Input / Window, Door 出力
Junction_9
    -> Junction_72
Note: AttributeManager_11 : Output / 屋内の Door, Window
Junction_72
    -> FeatureTypeFilter_3
FeatureTypeFilter_3
    ATTRIBUTES = Door,Window,<Blank>,<Unfiltered>
    Door -> GeometryPropertySetter_2
    Window -> GeometryPropertySetter_3
GeometryPropertySetter_2
    GQUERY:
      for $geom in //geometry
      where $geom/count(parent::geometry) = 0
      return number($geom/@fme_id)
    OVERWRITE_CHOICE = Yes
    REMOVE_ATTRIBUTE = Yes
    SETTYPE_PARAM = Traits From Attributes
    SRC_ATTRS = citygml_lod_name gml_id
    SET -> AttributeCreator_8
AttributeCreator_8
    ATTR_TABLE = SET_TO gml_id = door_@UUID()
    -> PLATEAU.IfcReprojector_6 [IfcFeature]
PLATEAU.IfcReprojector_6
    DEST_COORDSYS = $(DEST_COORDSYS)
    LENGTH_MULTIPLIER = @Value(_lengthmultiplier)
    REPROJECTION_PARAMS = @Value(_reprojection_params)
    Reprojected -> FeatureMerger_AttrDoor [REQUESTOR]
Note: 属性結合
FeatureMerger_AttrDoor
    ATTR_ACCUM_MODE = Merge Supplier
    ATTR_CONFLICT_RES = Use Requestor
    IGNORE_NULLS = No
    JOIN_KEYS = @Value(ifc_unique_id) @Value(ifc_unique_id) AUTO
    MERGE_TYPE = Attributes Only
    PROCESS_DUPS = NO
    REJECT_NULL_MISSING_KEYS = No
    SUPPLIERS_FIRST = No
    MERGED -> Door (writer CITYGML_2)
Door (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, uro_ifc_opening_attribute{}.uro_ifc_building_uro_global_id xml_buffer, uro_ifc_opening_attribute{}.uro_ifc_building_uro_name xml_buffer, uro_ifc_opening_attribute{}.uro_ifc_building_uro_description xml_buffer, uro_ifc_opening_attribute{}.uro_ifc_building_uro_object_type xml_buffer, uro_ifc_opening_attribute{}.uro_ifc_building_uro_long_name xml_buffer, uro_ifc_opening_attribute{}.uro_ifc_building_uro_composition_type xml_char(7), uro_ifc_opening_attribute{}.uro_ifc_building_uro_elevation_of_ref_height xml_real64, uro_ifc_opening_attribute{}.uro_ifc_building_uro_elevation_of_ref_height_units xml_buffer, uro_ifc_opening_attribute{}.uro_ifc_building_uro_elevation_of_terrain xml_real64, uro_ifc_opening_attribute{}.uro_ifc_building_uro_elevation_of_terrain_units xml_buffer, uro_ifc_opening_attribute{}.uro_ifc_building_uro_building_address_xlink_href xml_buffer, uro_ifc_opening_attribute{}.uro_ifc_building_element_uro_global_id xml_buffer, uro_ifc_opening_attribute{}.uro_ifc_building_element_uro_name xml_buffer, uro_ifc_opening_attribute{}.uro_ifc_building_element_uro_description xml_buffer, uro_ifc_opening_attribute{}.uro_ifc_building_element_uro_object_type xml_buffer,
      uro_ifc_opening_attribute{}.uro_ifc_building_element_uro_tag xml_buffer, uro_ifc_opening_attribute{}.uro_ifc_building_element_uro_element_type xml_buffer, uro_ifc_opening_attribute{}.uro_ifc_building_element_uro_element_type_codeSpace xml_buffer, uro_ifc_opening_attribute{}.uro_ifc_building_element_uro_predefined_type xml_buffer, uro_ifc_opening_attribute{}.uro_ifc_building_element_uro_predefined_type_codeSpace xml_buffer, uro_ifc_opening_attribute{}.uro_ifc_building_element_uro_shape_type xml_buffer, uro_ifc_opening_attribute{}.uro_ifc_building_element_uro_shape_type_codeSpace xml_buffer, uro_ifc_opening_attribute{}.uro_ifc_building_element_uro_number_of_riser xml_int64, uro_ifc_opening_attribute{}.uro_ifc_building_element_uro_number_of_treads xml_int64, uro_ifc_opening_attribute{}.uro_ifc_building_element_uro_riser_height xml_int64, uro_ifc_opening_attribute{}.uro_ifc_building_element_uro_tread_length xml_int64, uro_ifc_opening_attribute{}.uro_ifc_building_element_uro_operation_type xml_char(11), uro_ifc_opening_attribute{}.uro_ifc_building_element_uro_capacity_by_weight xml_real64, uro_ifc_opening_attribute{}.uro_ifc_building_element_uro_capacity_by_weight_units xml_buffer, uro_ifc_opening_attribute{}.uro_ifc_building_element_uro_capacity_by_number xml_int64, uro_ifc_opening_attribute{}.uro_ifc_building_storey_uro_global_id xml_buffer, uro_ifc_opening_attribute{}.uro_ifc_building_storey_uro_name xml_buffer, uro_ifc_opening_attribute{}.uro_ifc_building_storey_uro_description xml_buffer, uro_ifc_opening_attribute{}.uro_ifc_building_storey_uro_object_type xml_buffer, uro_ifc_opening_attribute{}.uro_ifc_building_storey_uro_long_name xml_buffer, uro_ifc_opening_attribute{}.uro_ifc_building_storey_uro_composition_type xml_char(7), uro_ifc_opening_attribute{}.uro_ifc_building_storey_uro_elevation xml_real64, uro_ifc_opening_attribute{}.uro_ifc_building_storey_uro_elevation_units xml_buffer, uro_ifc_opening_attribute{}.uro_ifc_classification_reference_uro_location xml_buffer, uro_ifc_opening_attribute{}.uro_ifc_classification_reference_uro_item_reference xml_buffer, uro_ifc_opening_attribute{}.uro_ifc_classification_reference_uro_item_reference_codeSpace xml_buffer, uro_ifc_opening_attribute{}.uro_ifc_classification_reference_uro_name xml_buffer, uro_ifc_opening_attribute{}.uro_ifc_classification_reference_uro_name_codeSpace xml_buffer, uro_ifc_opening_attribute{}.uro_ifc_classification_reference_uro_reference_source_uro_ifc_classification_uro_source xml_buffer, uro_ifc_opening_attribute{}.uro_ifc_classification_reference_uro_reference_source_uro_ifc_classification_uro_edition xml_buffer,
      uro_ifc_opening_attribute{}.uro_ifc_classification_reference_uro_reference_source_uro_ifc_classification_uro_edition_date xml_date, uro_ifc_opening_attribute{}.uro_ifc_classification_reference_uro_reference_source_uro_ifc_classification_uro_name xml_buffer, uro_ifc_opening_attribute{}.uro_ifc_coordinate_reference_system_uro_name xml_buffer, uro_ifc_opening_attribute{}.uro_ifc_coordinate_reference_system_uro_description xml_buffer, uro_ifc_opening_attribute{}.uro_ifc_coordinate_reference_system_uro_geodetic_datum xml_buffer, uro_ifc_opening_attribute{}.uro_ifc_coordinate_reference_system_uro_vertical_datum xml_buffer, uro_ifc_opening_attribute{}.uro_ifc_curtain_wall_uro_global_id xml_buffer, uro_ifc_opening_attribute{}.uro_ifc_curtain_wall_uro_name xml_buffer, uro_ifc_opening_attribute{}.uro_ifc_curtain_wall_uro_description xml_buffer, uro_ifc_opening_attribute{}.uro_ifc_curtain_wall_uro_object_type xml_buffer, uro_ifc_opening_attribute{}.uro_ifc_curtain_wall_uro_tag xml_buffer, uro_ifc_opening_attribute{}.uro_ifc_curtain_wall_uro_element_type xml_buffer, uro_ifc_opening_attribute{}.uro_ifc_curtain_wall_uro_element_type_codeSpace xml_buffer, uro_ifc_opening_attribute{}.uro_ifc_curtain_wall_uro_predefined_type xml_buffer, uro_ifc_opening_attribute{}.uro_ifc_curtain_wall_uro_predefined_type_codeSpace xml_buffer, uro_ifc_opening_attribute{}.uro_ifc_curtain_wall_uro_shape_type xml_buffer, uro_ifc_opening_attribute{}.uro_ifc_curtain_wall_uro_shape_type_codeSpace xml_buffer, uro_ifc_opening_attribute{}.uro_ifc_curtain_wall_uro_number_of_riser xml_int64, uro_ifc_opening_attribute{}.uro_ifc_curtain_wall_uro_number_of_treads xml_int64, uro_ifc_opening_attribute{}.uro_ifc_curtain_wall_uro_riser_height xml_int64, uro_ifc_opening_attribute{}.uro_ifc_curtain_wall_uro_tread_length xml_int64, uro_ifc_opening_attribute{}.uro_ifc_curtain_wall_uro_operation_type xml_char(11), uro_ifc_opening_attribute{}.uro_ifc_curtain_wall_uro_capacity_by_weight xml_real64, uro_ifc_opening_attribute{}.uro_ifc_curtain_wall_uro_capacity_by_weight_units xml_buffer, uro_ifc_opening_attribute{}.uro_ifc_curtain_wall_uro_capacity_by_number xml_int64, uro_ifc_opening_attribute{}.uro_ifc_door_uro_global_id xml_buffer, uro_ifc_opening_attribute{}.uro_ifc_door_uro_name xml_buffer, uro_ifc_opening_attribute{}.uro_ifc_door_uro_description xml_buffer, uro_ifc_opening_attribute{}.uro_ifc_door_uro_object_type xml_buffer, uro_ifc_opening_attribute{}.uro_ifc_door_uro_tag xml_buffer,
      uro_ifc_opening_attribute{}.uro_ifc_door_uro_element_type xml_buffer, uro_ifc_opening_attribute{}.uro_ifc_door_uro_element_type_codeSpace xml_buffer, uro_ifc_opening_attribute{}.uro_ifc_door_uro_predefined_type xml_buffer, uro_ifc_opening_attribute{}.uro_ifc_door_uro_predefined_type_codeSpace xml_buffer, uro_ifc_opening_attribute{}.uro_ifc_door_uro_shape_type xml_buffer, uro_ifc_opening_attribute{}.uro_ifc_door_uro_shape_type_codeSpace xml_buffer, uro_ifc_opening_attribute{}.uro_ifc_door_uro_number_of_riser xml_int64, uro_ifc_opening_attribute{}.uro_ifc_door_uro_number_of_treads xml_int64, uro_ifc_opening_attribute{}.uro_ifc_door_uro_riser_height xml_int64, uro_ifc_opening_attribute{}.uro_ifc_door_uro_tread_length xml_int64, uro_ifc_opening_attribute{}.uro_ifc_door_uro_operation_type xml_char(11), uro_ifc_opening_attribute{}.uro_ifc_door_uro_capacity_by_weight xml_real64, uro_ifc_opening_attribute{}.uro_ifc_door_uro_capacity_by_weight_units xml_buffer, uro_ifc_opening_attribute{}.uro_ifc_door_uro_capacity_by_number xml_int64, uro_ifc_opening_attribute{}.uro_ifc_door_uro_overall_height xml_real64, uro_ifc_opening_attribute{}.uro_ifc_door_uro_overall_height_units xml_buffer, uro_ifc_opening_attribute{}.uro_ifc_door_uro_overall_width xml_real64, uro_ifc_opening_attribute{}.uro_ifc_door_uro_overall_width_units xml_buffer, uro_ifc_opening_attribute{}.uro_ifc_furnishing_element_uro_global_id xml_buffer, uro_ifc_opening_attribute{}.uro_ifc_furnishing_element_uro_name xml_buffer, uro_ifc_opening_attribute{}.uro_ifc_furnishing_element_uro_description xml_buffer, uro_ifc_opening_attribute{}.uro_ifc_furnishing_element_uro_object_type xml_buffer, uro_ifc_opening_attribute{}.uro_ifc_furnishing_element_uro_tag xml_buffer, uro_ifc_opening_attribute{}.uro_ifc_map_conversion_uro_source_crs_uro_crs_uro_ifc_projected_crs_uro_name xml_buffer, uro_ifc_opening_attribute{}.uro_ifc_map_conversion_uro_source_crs_uro_crs_uro_ifc_projected_crs_uro_description xml_buffer, uro_ifc_opening_attribute{}.uro_ifc_map_conversion_uro_source_crs_uro_crs_uro_ifc_projected_crs_uro_geodetic_datum xml_buffer, uro_ifc_opening_attribute{}.uro_ifc_map_conversion_uro_source_crs_uro_crs_uro_ifc_projected_crs_uro_vertical_datum xml_buffer, uro_ifc_opening_attribute{}.uro_ifc_map_conversion_uro_source_crs_uro_crs_uro_ifc_projected_crs_uro_map_unit xml_buffer, uro_ifc_opening_attribute{}.uro_ifc_map_conversion_uro_source_crs_uro_crs_uro_ifc_projected_crs_uro_map_projection xml_buffer, uro_ifc_opening_attribute{}.uro_ifc_map_conversion_uro_source_crs_uro_crs_uro_ifc_projected_crs_uro_map_zone xml_buffer,
      uro_ifc_opening_attribute{}.uro_ifc_map_conversion_uro_source_crs_uro_crs_uro_ifc_coordinate_reference_system_uro_name xml_buffer, uro_ifc_opening_attribute{}.uro_ifc_map_conversion_uro_source_crs_uro_crs_uro_ifc_coordinate_reference_system_uro_description xml_buffer, uro_ifc_opening_attribute{}.uro_ifc_map_conversion_uro_source_crs_uro_crs_uro_ifc_coordinate_reference_system_uro_geodetic_datum xml_buffer, uro_ifc_opening_attribute{}.uro_ifc_map_conversion_uro_source_crs_uro_crs_uro_ifc_coordinate_reference_system_uro_vertical_datum xml_buffer, uro_ifc_opening_attribute{}.uro_ifc_map_conversion_uro_source_crs_uro_context_uro_ifc_geometric_representation_context_uro_context_identifier xml_buffer, uro_ifc_opening_attribute{}.uro_ifc_map_conversion_uro_source_crs_uro_context_uro_ifc_geometric_representation_context_uro_context_type xml_buffer, uro_ifc_opening_attribute{}.uro_ifc_map_conversion_uro_source_crs_uro_context_uro_ifc_geometric_representation_context_uro_coordinate_space_dimension xml_int64, uro_ifc_opening_attribute{}.uro_ifc_map_conversion_uro_source_crs_uro_context_uro_ifc_geometric_representation_context_uro_precision xml_real64, uro_ifc_opening_attribute{}.uro_ifc_map_conversion_uro_source_crs_uro_context_uro_ifc_geometric_representation_context_uro_true_north xml_real64, uro_ifc_opening_attribute{}.uro_ifc_map_conversion_uro_target_crs_uro_ifc_projected_crs_uro_name xml_buffer, uro_ifc_opening_attribute{}.uro_ifc_map_conversion_uro_target_crs_uro_ifc_projected_crs_uro_description xml_buffer, uro_ifc_opening_attribute{}.uro_ifc_map_conversion_uro_target_crs_uro_ifc_projected_crs_uro_geodetic_datum xml_buffer, uro_ifc_opening_attribute{}.uro_ifc_map_conversion_uro_target_crs_uro_ifc_projected_crs_uro_vertical_datum xml_buffer, uro_ifc_opening_attribute{}.uro_ifc_map_conversion_uro_target_crs_uro_ifc_projected_crs_uro_map_unit xml_buffer, uro_ifc_opening_attribute{}.uro_ifc_map_conversion_uro_target_crs_uro_ifc_projected_crs_uro_map_projection xml_buffer, uro_ifc_opening_attribute{}.uro_ifc_map_conversion_uro_target_crs_uro_ifc_projected_crs_uro_map_zone xml_buffer, uro_ifc_opening_attribute{}.uro_ifc_map_conversion_uro_target_crs_uro_ifc_coordinate_reference_system_uro_name xml_buffer, uro_ifc_opening_attribute{}.uro_ifc_map_conversion_uro_target_crs_uro_ifc_coordinate_reference_system_uro_description xml_buffer, uro_ifc_opening_attribute{}.uro_ifc_map_conversion_uro_target_crs_uro_ifc_coordinate_reference_system_uro_geodetic_datum xml_buffer, uro_ifc_opening_attribute{}.uro_ifc_map_conversion_uro_target_crs_uro_ifc_coordinate_reference_system_uro_vertical_datum xml_buffer, uro_ifc_opening_attribute{}.uro_ifc_map_conversion_uro_eastings xml_buffer, uro_ifc_opening_attribute{}.uro_ifc_map_conversion_uro_northings xml_buffer, uro_ifc_opening_attribute{}.uro_ifc_map_conversion_uro_orthogonal_height xml_real64, uro_ifc_opening_attribute{}.uro_ifc_map_conversion_uro_orthogonal_height_units xml_buffer, uro_ifc_opening_attribute{}.uro_ifc_map_conversion_uro_x_axis_abscissa xml_real64, uro_ifc_opening_attribute{}.uro_ifc_map_conversion_uro_x_axis_ordinate xml_real64, uro_ifc_opening_attribute{}.uro_ifc_map_conversion_uro_scale xml_real64, uro_ifc_opening_attribute{}.uro_ifc_opening_element_uro_global_id xml_buffer, uro_ifc_opening_attribute{}.uro_ifc_opening_element_uro_name xml_buffer, uro_ifc_opening_attribute{}.uro_ifc_opening_element_uro_description xml_buffer,
      uro_ifc_opening_attribute{}.uro_ifc_opening_element_uro_object_type xml_buffer, uro_ifc_opening_attribute{}.uro_ifc_opening_element_uro_tag xml_buffer, uro_ifc_opening_attribute{}.uro_ifc_opening_element_uro_nominal_area xml_real64, uro_ifc_opening_attribute{}.uro_ifc_opening_element_uro_nominal_area_units xml_buffer, uro_ifc_opening_attribute{}.uro_ifc_opening_element_uro_nominal_volume xml_real64, uro_ifc_opening_attribute{}.uro_ifc_opening_element_uro_nominal_volume_units xml_buffer, uro_ifc_opening_attribute{}.uro_ifc_project_uro_global_id xml_buffer, uro_ifc_opening_attribute{}.uro_ifc_project_uro_name xml_buffer, uro_ifc_opening_attribute{}.uro_ifc_project_uro_description xml_buffer, uro_ifc_opening_attribute{}.uro_ifc_project_uro_object_type xml_buffer, uro_ifc_opening_attribute{}.uro_ifc_project_uro_long_name xml_buffer, uro_ifc_opening_attribute{}.uro_ifc_project_uro_phase xml_buffer, uro_ifc_opening_attribute{}.uro_ifc_project_uro_representation_contexts_uro_ifc_geometric_representation_context_uro_context_identifier xml_buffer, uro_ifc_opening_attribute{}.uro_ifc_project_uro_representation_contexts_uro_ifc_geometric_representation_context_uro_context_type xml_buffer, uro_ifc_opening_attribute{}.uro_ifc_project_uro_representation_contexts_uro_ifc_geometric_representation_context_uro_coordinate_space_dimension xml_int64, uro_ifc_opening_attribute{}.uro_ifc_project_uro_representation_contexts_uro_ifc_geometric_representation_context_uro_precision xml_real64, uro_ifc_opening_attribute{}.uro_ifc_project_uro_representation_contexts_uro_ifc_geometric_representation_context_uro_true_north xml_real64, uro_ifc_opening_attribute{}.uro_ifc_project_uro_units_in_context{}.uro_ifc_unit_uro_dimensions xml_int64, uro_ifc_opening_attribute{}.uro_ifc_project_uro_units_in_context{}.uro_ifc_unit_uro_unit_type xml_char(28), uro_ifc_opening_attribute{}.uro_ifc_project_uro_units_in_context{}.uro_ifc_unit_uro_perfix xml_buffer, uro_ifc_opening_attribute{}.uro_ifc_project_uro_units_in_context{}.uro_ifc_unit_uro_name xml_buffer, uro_ifc_opening_attribute{}.uro_ifc_projected_crs_uro_name xml_buffer, uro_ifc_opening_attribute{}.uro_ifc_projected_crs_uro_description xml_buffer, uro_ifc_opening_attribute{}.uro_ifc_projected_crs_uro_geodetic_datum xml_buffer, uro_ifc_opening_attribute{}.uro_ifc_projected_crs_uro_vertical_datum xml_buffer, uro_ifc_opening_attribute{}.uro_ifc_projected_crs_uro_map_unit xml_buffer, uro_ifc_opening_attribute{}.uro_ifc_projected_crs_uro_map_projection xml_buffer, uro_ifc_opening_attribute{}.uro_ifc_projected_crs_uro_map_zone xml_buffer, uro_ifc_opening_attribute{}.uro_ifc_pset_building_common_uro_building_id xml_real64, uro_ifc_opening_attribute{}.uro_ifc_pset_building_common_uro_building_id_units xml_buffer,
      uro_ifc_opening_attribute{}.uro_ifc_pset_building_common_uro_is_permanent_id xml_real64, uro_ifc_opening_attribute{}.uro_ifc_pset_building_common_uro_is_permanent_id_units xml_buffer, uro_ifc_opening_attribute{}.uro_ifc_pset_building_common_uro_main_fire_use xml_buffer, uro_ifc_opening_attribute{}.uro_ifc_pset_building_common_uro_ancillary_fire_use xml_buffer, uro_ifc_opening_attribute{}.uro_ifc_pset_building_common_uro_sprinkler_protection xml_boolean, uro_ifc_opening_attribute{}.uro_ifc_pset_building_common_uro_sprinkler_protection_automatic xml_boolean, uro_ifc_opening_attribute{}.uro_ifc_pset_building_common_uro_occupancy_type xml_buffer, uro_ifc_opening_attribute{}.uro_ifc_pset_building_common_uro_occupancy_type_codeSpace xml_buffer, uro_ifc_opening_attribute{}.uro_ifc_pset_building_common_uro_gross_planned_area xml_real64, uro_ifc_opening_attribute{}.uro_ifc_pset_building_common_uro_gross_planned_area_units xml_buffer, uro_ifc_opening_attribute{}.uro_ifc_pset_building_common_uro_number_of_storeys xml_int64, uro_ifc_opening_attribute{}.uro_ifc_pset_building_common_uro_year_of_construction xml_buffer, uro_ifc_opening_attribute{}.uro_ifc_pset_building_common_uro_is_landmarked xml_boolean, uro_ifc_opening_attribute{}.uro_ifc_pset_door_common_uro_reference xml_buffer, uro_ifc_opening_attribute{}.uro_ifc_pset_door_common_uro_acoustic_rating xml_buffer, uro_ifc_opening_attribute{}.uro_ifc_pset_door_common_uro_firerating xml_buffer, uro_ifc_opening_attribute{}.uro_ifc_pset_door_common_uro_security_rating xml_buffer, uro_ifc_opening_attribute{}.uro_ifc_pset_door_common_uro_is_external xml_boolean, uro_ifc_opening_attribute{}.uro_ifc_pset_door_common_uro_infiltration xml_real64, uro_ifc_opening_attribute{}.uro_ifc_pset_door_common_uro_thermal_transmittance xml_real64, uro_ifc_opening_attribute{}.uro_ifc_pset_door_common_uro_glazing_area_fraction xml_real64, uro_ifc_opening_attribute{}.uro_ifc_pset_door_common_uro_handicap_accessible xml_real64, uro_ifc_opening_attribute{}.uro_ifc_pset_door_common_uro_fire_exit xml_boolean, uro_ifc_opening_attribute{}.uro_ifc_pset_door_common_uro_self_closing xml_real64, uro_ifc_opening_attribute{}.uro_ifc_pset_door_common_uro_smoke_stop xml_boolean, uro_ifc_opening_attribute{}.uro_ifc_pset_opening_element_common_uro_reference xml_buffer, uro_ifc_opening_attribute{}.uro_ifc_pset_opening_element_common_uro_purpose xml_buffer, uro_ifc_opening_attribute{}.uro_ifc_pset_opening_element_common_uro_fire_exit xml_boolean, uro_ifc_opening_attribute{}.uro_ifc_pset_opening_element_common_uro_protected_opening xml_boolean, uro_ifc_opening_attribute{}.uro_ifc_pset_opening_element_common_uro_parallel_jambs xml_boolean,
      uro_ifc_opening_attribute{}.uro_ifc_pset_site_common_uro_buildable_area xml_real64, uro_ifc_opening_attribute{}.uro_ifc_pset_site_common_uro_buildable_area_units xml_buffer, uro_ifc_opening_attribute{}.uro_ifc_pset_site_common_uro_total_area xml_real64, uro_ifc_opening_attribute{}.uro_ifc_pset_site_common_uro_total_area_units xml_buffer, uro_ifc_opening_attribute{}.uro_ifc_pset_site_common_uro_building_height_limit xml_real64, uro_ifc_opening_attribute{}.uro_ifc_pset_site_common_uro_building_height_limit_units xml_buffer, uro_ifc_opening_attribute{}.uro_ifc_pset_space_common_uro_reference xml_buffer, uro_ifc_opening_attribute{}.uro_ifc_pset_space_common_uro_category xml_buffer, uro_ifc_opening_attribute{}.uro_ifc_pset_space_common_uro_category_codeSpace xml_buffer, uro_ifc_opening_attribute{}.uro_ifc_pset_space_common_uro_floor_covering xml_buffer, uro_ifc_opening_attribute{}.uro_ifc_pset_space_common_uro_wall_covering xml_buffer, uro_ifc_opening_attribute{}.uro_ifc_pset_space_common_uro_ceiling_covering xml_buffer, uro_ifc_opening_attribute{}.uro_ifc_pset_space_common_uro_skirting_covering xml_buffer, uro_ifc_opening_attribute{}.uro_ifc_pset_space_common_uro_gross_planned_area xml_real64, uro_ifc_opening_attribute{}.uro_ifc_pset_space_common_uro_gross_planned_area_units xml_buffer, uro_ifc_opening_attribute{}.uro_ifc_pset_space_common_uro_net_planned_area xml_real64, uro_ifc_opening_attribute{}.uro_ifc_pset_space_common_uro_net_planned_area_units xml_buffer, uro_ifc_opening_attribute{}.uro_ifc_pset_space_common_uro_publicly_accessible xml_boolean, uro_ifc_opening_attribute{}.uro_ifc_pset_space_common_uro_handicap_accessible xml_boolean, uro_ifc_opening_attribute{}.uro_ifc_pset_space_common_uro_concealed_flooring xml_boolean, uro_ifc_opening_attribute{}.uro_ifc_pset_space_common_uro_concealed_ceiling xml_boolean, uro_ifc_opening_attribute{}.uro_ifc_pset_window_common_uro_reference xml_buffer, uro_ifc_opening_attribute{}.uro_ifc_pset_window_common_uro_acoustic_rating xml_buffer, uro_ifc_opening_attribute{}.uro_ifc_pset_window_common_uro_firerating xml_buffer, uro_ifc_opening_attribute{}.uro_ifc_pset_window_common_uro_security_rating xml_buffer, uro_ifc_opening_attribute{}.uro_ifc_pset_window_common_uro_is_external xml_boolean, uro_ifc_opening_attribute{}.uro_ifc_pset_window_common_uro_infiltration xml_real64, uro_ifc_opening_attribute{}.uro_ifc_pset_window_common_uro_thermal_transmittance xml_real64, uro_ifc_opening_attribute{}.uro_ifc_pset_window_common_uro_glazing_area_fraction xml_real64, uro_ifc_opening_attribute{}.uro_ifc_pset_window_common_uro_smoke_stop xml_boolean,
      uro_ifc_opening_attribute{}.uro_ifc_site_uro_global_id xml_buffer, uro_ifc_opening_attribute{}.uro_ifc_site_uro_name xml_buffer, uro_ifc_opening_attribute{}.uro_ifc_site_uro_description xml_buffer, uro_ifc_opening_attribute{}.uro_ifc_site_uro_object_type xml_buffer, uro_ifc_opening_attribute{}.uro_ifc_site_uro_long_name xml_buffer, uro_ifc_opening_attribute{}.uro_ifc_site_uro_composition_type xml_char(7), uro_ifc_opening_attribute{}.uro_ifc_site_uro_ref_longitude xml_real64, uro_ifc_opening_attribute{}.uro_ifc_site_uro_ref_latitude xml_real64, uro_ifc_opening_attribute{}.uro_ifc_site_uro_ref_elevation xml_real64, uro_ifc_opening_attribute{}.uro_ifc_site_uro_ref_elevation_units xml_buffer, uro_ifc_opening_attribute{}.uro_ifc_site_uro_land_title_number xml_buffer, uro_ifc_opening_attribute{}.uro_ifc_site_uro_site_address_xlink_href xml_buffer, uro_ifc_opening_attribute{}.uro_ifc_space_uro_global_id xml_buffer, uro_ifc_opening_attribute{}.uro_ifc_space_uro_name xml_buffer, uro_ifc_opening_attribute{}.uro_ifc_space_uro_description xml_buffer, uro_ifc_opening_attribute{}.uro_ifc_space_uro_object_type xml_buffer, uro_ifc_opening_attribute{}.uro_ifc_space_uro_long_name xml_buffer, uro_ifc_opening_attribute{}.uro_ifc_space_uro_composition_type xml_char(7), uro_ifc_opening_attribute{}.uro_ifc_space_uro_interioror_exterior_space xml_char(10), uro_ifc_opening_attribute{}.uro_ifc_space_uro_elevation_with_flooring xml_real64, uro_ifc_opening_attribute{}.uro_ifc_space_uro_elevation_with_flooring_units xml_buffer, uro_ifc_opening_attribute{}.uro_ifc_space_base_quantity_uro_nominal_height xml_real64, uro_ifc_opening_attribute{}.uro_ifc_space_base_quantity_uro_nominal_height_units xml_buffer, uro_ifc_opening_attribute{}.uro_ifc_space_base_quantity_uro_clear_height xml_real64, uro_ifc_opening_attribute{}.uro_ifc_space_base_quantity_uro_clear_height_units xml_buffer, uro_ifc_opening_attribute{}.uro_ifc_space_base_quantity_uro_finish_ceiling_height xml_real64, uro_ifc_opening_attribute{}.uro_ifc_space_base_quantity_uro_finish_ceiling_height_units xml_buffer, uro_ifc_opening_attribute{}.uro_ifc_space_base_quantity_uro_gross_perimeter xml_real64, uro_ifc_opening_attribute{}.uro_ifc_space_base_quantity_uro_gross_perimeter_units xml_buffer, uro_ifc_opening_attribute{}.uro_ifc_space_base_quantity_uro_net_perimeter xml_real64,
      uro_ifc_opening_attribute{}.uro_ifc_space_base_quantity_uro_net_perimeter_units xml_buffer, uro_ifc_opening_attribute{}.uro_ifc_space_base_quantity_uro_gross_ceiling_area xml_real64, uro_ifc_opening_attribute{}.uro_ifc_space_base_quantity_uro_gross_ceiling_area_units xml_buffer, uro_ifc_opening_attribute{}.uro_ifc_space_base_quantity_uro_gross_floor_area xml_real64, uro_ifc_opening_attribute{}.uro_ifc_space_base_quantity_uro_gross_floor_area_units xml_buffer, uro_ifc_opening_attribute{}.uro_ifc_space_base_quantity_uro_net_ceiling_area xml_real64, uro_ifc_opening_attribute{}.uro_ifc_space_base_quantity_uro_net_ceiling_area_units xml_buffer, uro_ifc_opening_attribute{}.uro_ifc_space_base_quantity_uro_net_floor_area xml_real64, uro_ifc_opening_attribute{}.uro_ifc_space_base_quantity_uro_net_floor_area_units xml_buffer, uro_ifc_opening_attribute{}.uro_ifc_space_base_quantity_uro_gross_wall_area xml_real64, uro_ifc_opening_attribute{}.uro_ifc_space_base_quantity_uro_gross_wall_area_units xml_buffer, uro_ifc_opening_attribute{}.uro_ifc_space_base_quantity_uro_net_wall_area xml_real64, uro_ifc_opening_attribute{}.uro_ifc_space_base_quantity_uro_net_wall_area_units xml_buffer, uro_ifc_opening_attribute{}.uro_ifc_space_base_quantity_uro_gross_volume xml_real64, uro_ifc_opening_attribute{}.uro_ifc_space_base_quantity_uro_gross_volume_units xml_buffer, uro_ifc_opening_attribute{}.uro_ifc_space_base_quantity_uro_net_volume xml_real64, uro_ifc_opening_attribute{}.uro_ifc_space_base_quantity_uro_net_volume_units xml_buffer, uro_ifc_opening_attribute{}.uro_ifc_wall_uro_global_id xml_buffer, uro_ifc_opening_attribute{}.uro_ifc_wall_uro_name xml_buffer, uro_ifc_opening_attribute{}.uro_ifc_wall_uro_description xml_buffer, uro_ifc_opening_attribute{}.uro_ifc_wall_uro_object_type xml_buffer, uro_ifc_opening_attribute{}.uro_ifc_wall_uro_tag xml_buffer, uro_ifc_opening_attribute{}.uro_ifc_wall_uro_element_type xml_buffer, uro_ifc_opening_attribute{}.uro_ifc_wall_uro_element_type_codeSpace xml_buffer, uro_ifc_opening_attribute{}.uro_ifc_wall_uro_predefined_type xml_buffer, uro_ifc_opening_attribute{}.uro_ifc_wall_uro_predefined_type_codeSpace xml_buffer, uro_ifc_opening_attribute{}.uro_ifc_wall_uro_shape_type xml_buffer, uro_ifc_opening_attribute{}.uro_ifc_wall_uro_shape_type_codeSpace xml_buffer, uro_ifc_opening_attribute{}.uro_ifc_wall_uro_number_of_riser xml_int64, uro_ifc_opening_attribute{}.uro_ifc_wall_uro_number_of_treads xml_int64,
      uro_ifc_opening_attribute{}.uro_ifc_wall_uro_riser_height xml_int64, uro_ifc_opening_attribute{}.uro_ifc_wall_uro_tread_length xml_int64, uro_ifc_opening_attribute{}.uro_ifc_wall_uro_operation_type xml_char(11), uro_ifc_opening_attribute{}.uro_ifc_wall_uro_capacity_by_weight xml_real64, uro_ifc_opening_attribute{}.uro_ifc_wall_uro_capacity_by_weight_units xml_buffer, uro_ifc_opening_attribute{}.uro_ifc_wall_uro_capacity_by_number xml_int64, uro_ifc_opening_attribute{}.uro_ifc_wall_uro_nominal_length xml_real64, uro_ifc_opening_attribute{}.uro_ifc_wall_uro_nominal_length_units xml_buffer, uro_ifc_opening_attribute{}.uro_ifc_wall_uro_nominal_width xml_real64, uro_ifc_opening_attribute{}.uro_ifc_wall_uro_nominal_width_units xml_buffer, uro_ifc_opening_attribute{}.uro_ifc_wall_uro_nominal_height xml_real64, uro_ifc_opening_attribute{}.uro_ifc_wall_uro_nominal_height_units xml_buffer, uro_ifc_opening_attribute{}.uro_ifc_wall_uro_gross_foot_print_area xml_real64, uro_ifc_opening_attribute{}.uro_ifc_wall_uro_gross_foot_print_area_units xml_buffer, uro_ifc_opening_attribute{}.uro_ifc_wall_uro_net_foot_print_area xml_real64, uro_ifc_opening_attribute{}.uro_ifc_wall_uro_net_foot_print_area_units xml_buffer, uro_ifc_opening_attribute{}.uro_ifc_wall_uro_gross_side_area xml_real64, uro_ifc_opening_attribute{}.uro_ifc_wall_uro_gross_side_area_units xml_buffer, uro_ifc_opening_attribute{}.uro_ifc_wall_uro_net_side_area xml_real64, uro_ifc_opening_attribute{}.uro_ifc_wall_uro_net_side_area_units xml_buffer, uro_ifc_opening_attribute{}.uro_ifc_wall_uro_gross_side_area_left xml_real64, uro_ifc_opening_attribute{}.uro_ifc_wall_uro_gross_side_area_left_units xml_buffer, uro_ifc_opening_attribute{}.uro_ifc_wall_uro_net_side_area_left xml_real64, uro_ifc_opening_attribute{}.uro_ifc_wall_uro_net_side_area_left_units xml_buffer, uro_ifc_opening_attribute{}.uro_ifc_wall_uro_gross_side_area_right xml_real64, uro_ifc_opening_attribute{}.uro_ifc_wall_uro_gross_side_area_right_units xml_buffer, uro_ifc_opening_attribute{}.uro_ifc_wall_uro_net_side_area_right xml_real64, uro_ifc_opening_attribute{}.uro_ifc_wall_uro_net_side_area_right_units xml_buffer, uro_ifc_opening_attribute{}.uro_ifc_wall_uro_gross_volume xml_real64, uro_ifc_opening_attribute{}.uro_ifc_wall_uro_gross_volume_units xml_buffer,
      uro_ifc_opening_attribute{}.uro_ifc_wall_uro_net_volume xml_real64, uro_ifc_opening_attribute{}.uro_ifc_wall_uro_net_volume_units xml_buffer, uro_ifc_opening_attribute{}.uro_ifc_wall_standard_case_uro_global_id xml_buffer, uro_ifc_opening_attribute{}.uro_ifc_wall_standard_case_uro_name xml_buffer, uro_ifc_opening_attribute{}.uro_ifc_wall_standard_case_uro_description xml_buffer, uro_ifc_opening_attribute{}.uro_ifc_wall_standard_case_uro_object_type xml_buffer, uro_ifc_opening_attribute{}.uro_ifc_wall_standard_case_uro_tag xml_buffer, uro_ifc_opening_attribute{}.uro_ifc_wall_standard_case_uro_element_type xml_buffer, uro_ifc_opening_attribute{}.uro_ifc_wall_standard_case_uro_element_type_codeSpace xml_buffer, uro_ifc_opening_attribute{}.uro_ifc_wall_standard_case_uro_predefined_type xml_buffer, uro_ifc_opening_attribute{}.uro_ifc_wall_standard_case_uro_predefined_type_codeSpace xml_buffer, uro_ifc_opening_attribute{}.uro_ifc_wall_standard_case_uro_shape_type xml_buffer, uro_ifc_opening_attribute{}.uro_ifc_wall_standard_case_uro_shape_type_codeSpace xml_buffer, uro_ifc_opening_attribute{}.uro_ifc_wall_standard_case_uro_number_of_riser xml_int64, uro_ifc_opening_attribute{}.uro_ifc_wall_standard_case_uro_number_of_treads xml_int64, uro_ifc_opening_attribute{}.uro_ifc_wall_standard_case_uro_riser_height xml_int64, uro_ifc_opening_attribute{}.uro_ifc_wall_standard_case_uro_tread_length xml_int64, uro_ifc_opening_attribute{}.uro_ifc_wall_standard_case_uro_operation_type xml_char(11), uro_ifc_opening_attribute{}.uro_ifc_wall_standard_case_uro_capacity_by_weight xml_real64, uro_ifc_opening_attribute{}.uro_ifc_wall_standard_case_uro_capacity_by_weight_units xml_buffer, uro_ifc_opening_attribute{}.uro_ifc_wall_standard_case_uro_capacity_by_number xml_int64, uro_ifc_opening_attribute{}.uro_ifc_wall_standard_case_uro_nominal_length xml_real64, uro_ifc_opening_attribute{}.uro_ifc_wall_standard_case_uro_nominal_length_units xml_buffer, uro_ifc_opening_attribute{}.uro_ifc_wall_standard_case_uro_nominal_width xml_real64, uro_ifc_opening_attribute{}.uro_ifc_wall_standard_case_uro_nominal_width_units xml_buffer, uro_ifc_opening_attribute{}.uro_ifc_wall_standard_case_uro_nominal_height xml_real64, uro_ifc_opening_attribute{}.uro_ifc_wall_standard_case_uro_nominal_height_units xml_buffer, uro_ifc_opening_attribute{}.uro_ifc_wall_standard_case_uro_gross_foot_print_area xml_real64, uro_ifc_opening_attribute{}.uro_ifc_wall_standard_case_uro_gross_foot_print_area_units xml_buffer, uro_ifc_opening_attribute{}.uro_ifc_wall_standard_case_uro_net_foot_print_area xml_real64,
      uro_ifc_opening_attribute{}.uro_ifc_wall_standard_case_uro_net_foot_print_area_units xml_buffer, uro_ifc_opening_attribute{}.uro_ifc_wall_standard_case_uro_gross_side_area xml_real64, uro_ifc_opening_attribute{}.uro_ifc_wall_standard_case_uro_gross_side_area_units xml_buffer, uro_ifc_opening_attribute{}.uro_ifc_wall_standard_case_uro_net_side_area xml_real64, uro_ifc_opening_attribute{}.uro_ifc_wall_standard_case_uro_net_side_area_units xml_buffer, uro_ifc_opening_attribute{}.uro_ifc_wall_standard_case_uro_gross_side_area_left xml_real64, uro_ifc_opening_attribute{}.uro_ifc_wall_standard_case_uro_gross_side_area_left_units xml_buffer, uro_ifc_opening_attribute{}.uro_ifc_wall_standard_case_uro_net_side_area_left xml_real64, uro_ifc_opening_attribute{}.uro_ifc_wall_standard_case_uro_net_side_area_left_units xml_buffer, uro_ifc_opening_attribute{}.uro_ifc_wall_standard_case_uro_gross_side_area_right xml_real64, uro_ifc_opening_attribute{}.uro_ifc_wall_standard_case_uro_gross_side_area_right_units xml_buffer, uro_ifc_opening_attribute{}.uro_ifc_wall_standard_case_uro_net_side_area_right xml_real64, uro_ifc_opening_attribute{}.uro_ifc_wall_standard_case_uro_net_side_area_right_units xml_buffer, uro_ifc_opening_attribute{}.uro_ifc_wall_standard_case_uro_gross_volume xml_real64, uro_ifc_opening_attribute{}.uro_ifc_wall_standard_case_uro_gross_volume_units xml_buffer, uro_ifc_opening_attribute{}.uro_ifc_wall_standard_case_uro_net_volume xml_real64, uro_ifc_opening_attribute{}.uro_ifc_wall_standard_case_uro_net_volume_units xml_buffer, uro_ifc_opening_attribute{}.uro_ifc_window_uro_global_id xml_buffer, uro_ifc_opening_attribute{}.uro_ifc_window_uro_name xml_buffer, uro_ifc_opening_attribute{}.uro_ifc_window_uro_description xml_buffer, uro_ifc_opening_attribute{}.uro_ifc_window_uro_object_type xml_buffer, uro_ifc_opening_attribute{}.uro_ifc_window_uro_tag xml_buffer, uro_ifc_opening_attribute{}.uro_ifc_window_uro_element_type xml_buffer, uro_ifc_opening_attribute{}.uro_ifc_window_uro_element_type_codeSpace xml_buffer, uro_ifc_opening_attribute{}.uro_ifc_window_uro_predefined_type xml_buffer, uro_ifc_opening_attribute{}.uro_ifc_window_uro_predefined_type_codeSpace xml_buffer, uro_ifc_opening_attribute{}.uro_ifc_window_uro_shape_type xml_buffer, uro_ifc_opening_attribute{}.uro_ifc_window_uro_shape_type_codeSpace xml_buffer, uro_ifc_opening_attribute{}.uro_ifc_window_uro_number_of_riser xml_int64, uro_ifc_opening_attribute{}.uro_ifc_window_uro_number_of_treads xml_int64,
      uro_ifc_opening_attribute{}.uro_ifc_window_uro_riser_height xml_int64, uro_ifc_opening_attribute{}.uro_ifc_window_uro_tread_length xml_int64, uro_ifc_opening_attribute{}.uro_ifc_window_uro_operation_type xml_char(11), uro_ifc_opening_attribute{}.uro_ifc_window_uro_capacity_by_weight xml_real64, uro_ifc_opening_attribute{}.uro_ifc_window_uro_capacity_by_weight_units xml_buffer, uro_ifc_opening_attribute{}.uro_ifc_window_uro_capacity_by_number xml_int64, uro_ifc_opening_attribute{}.uro_ifc_window_uro_overall_height xml_real64, uro_ifc_opening_attribute{}.uro_ifc_window_uro_overall_height_units xml_buffer, uro_ifc_opening_attribute{}.uro_ifc_window_uro_overall_width xml_real64, uro_ifc_opening_attribute{}.uro_ifc_window_uro_overall_width_units xml_buffer, citygml_address{}.xlink_href xml_buffer
GeometryPropertySetter_3
    GQUERY:
      for $geom in //geometry
      where $geom/count(parent::geometry) = 0
      return number($geom/@fme_id)
    OVERWRITE_CHOICE = Yes
    REMOVE_ATTRIBUTE = Yes
    SETTYPE_PARAM = Traits From Attributes
    SRC_ATTRS = citygml_lod_name gml_id
    SET -> AttributeCreator_9
AttributeCreator_9
    ATTR_TABLE = SET_TO gml_id = wnd_@UUID()
    -> PLATEAU.IfcReprojector_7 [IfcFeature]
PLATEAU.IfcReprojector_7
    DEST_COORDSYS = $(DEST_COORDSYS)
    LENGTH_MULTIPLIER = @Value(_lengthmultiplier)
    REPROJECTION_PARAMS = @Value(_reprojection_params)
    Reprojected -> FeatureMerger_AttrWindow [REQUESTOR]
Note: 属性結合
FeatureMerger_AttrWindow
    ATTR_ACCUM_MODE = Merge Supplier
    ATTR_CONFLICT_RES = Use Requestor
    IGNORE_NULLS = No
    JOIN_KEYS = @Value(ifc_unique_id) @Value(ifc_unique_id) AUTO
    MERGE_TYPE = Attributes Only
    PROCESS_DUPS = NO
    REJECT_NULL_MISSING_KEYS = No
    SUPPLIERS_FIRST = No
    MERGED -> Window (writer CITYGML_2)
Window (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, uro_ifc_opening_attribute{}.uro_ifc_building_uro_global_id xml_buffer, uro_ifc_opening_attribute{}.uro_ifc_building_uro_name xml_buffer, uro_ifc_opening_attribute{}.uro_ifc_building_uro_description xml_buffer, uro_ifc_opening_attribute{}.uro_ifc_building_uro_object_type xml_buffer, uro_ifc_opening_attribute{}.uro_ifc_building_uro_long_name xml_buffer, uro_ifc_opening_attribute{}.uro_ifc_building_uro_composition_type xml_char(7), uro_ifc_opening_attribute{}.uro_ifc_building_uro_elevation_of_ref_height xml_real64, uro_ifc_opening_attribute{}.uro_ifc_building_uro_elevation_of_ref_height_units xml_buffer, uro_ifc_opening_attribute{}.uro_ifc_building_uro_elevation_of_terrain xml_real64, uro_ifc_opening_attribute{}.uro_ifc_building_uro_elevation_of_terrain_units xml_buffer, uro_ifc_opening_attribute{}.uro_ifc_building_uro_building_address_xlink_href xml_buffer, uro_ifc_opening_attribute{}.uro_ifc_building_element_uro_global_id xml_buffer, uro_ifc_opening_attribute{}.uro_ifc_building_element_uro_name xml_buffer, uro_ifc_opening_attribute{}.uro_ifc_building_element_uro_description xml_buffer, uro_ifc_opening_attribute{}.uro_ifc_building_element_uro_object_type xml_buffer,
      uro_ifc_opening_attribute{}.uro_ifc_building_element_uro_tag xml_buffer, uro_ifc_opening_attribute{}.uro_ifc_building_element_uro_element_type xml_buffer, uro_ifc_opening_attribute{}.uro_ifc_building_element_uro_element_type_codeSpace xml_buffer, uro_ifc_opening_attribute{}.uro_ifc_building_element_uro_predefined_type xml_buffer, uro_ifc_opening_attribute{}.uro_ifc_building_element_uro_predefined_type_codeSpace xml_buffer, uro_ifc_opening_attribute{}.uro_ifc_building_element_uro_shape_type xml_buffer, uro_ifc_opening_attribute{}.uro_ifc_building_element_uro_shape_type_codeSpace xml_buffer, uro_ifc_opening_attribute{}.uro_ifc_building_element_uro_number_of_riser xml_int64, uro_ifc_opening_attribute{}.uro_ifc_building_element_uro_number_of_treads xml_int64, uro_ifc_opening_attribute{}.uro_ifc_building_element_uro_riser_height xml_int64, uro_ifc_opening_attribute{}.uro_ifc_building_element_uro_tread_length xml_int64, uro_ifc_opening_attribute{}.uro_ifc_building_element_uro_operation_type xml_char(11), uro_ifc_opening_attribute{}.uro_ifc_building_element_uro_capacity_by_weight xml_real64, uro_ifc_opening_attribute{}.uro_ifc_building_element_uro_capacity_by_weight_units xml_buffer, uro_ifc_opening_attribute{}.uro_ifc_building_element_uro_capacity_by_number xml_int64, uro_ifc_opening_attribute{}.uro_ifc_building_storey_uro_global_id xml_buffer, uro_ifc_opening_attribute{}.uro_ifc_building_storey_uro_name xml_buffer, uro_ifc_opening_attribute{}.uro_ifc_building_storey_uro_description xml_buffer, uro_ifc_opening_attribute{}.uro_ifc_building_storey_uro_object_type xml_buffer, uro_ifc_opening_attribute{}.uro_ifc_building_storey_uro_long_name xml_buffer, uro_ifc_opening_attribute{}.uro_ifc_building_storey_uro_composition_type xml_char(7), uro_ifc_opening_attribute{}.uro_ifc_building_storey_uro_elevation xml_real64, uro_ifc_opening_attribute{}.uro_ifc_building_storey_uro_elevation_units xml_buffer, uro_ifc_opening_attribute{}.uro_ifc_classification_reference_uro_location xml_buffer, uro_ifc_opening_attribute{}.uro_ifc_classification_reference_uro_item_reference xml_buffer, uro_ifc_opening_attribute{}.uro_ifc_classification_reference_uro_item_reference_codeSpace xml_buffer, uro_ifc_opening_attribute{}.uro_ifc_classification_reference_uro_name xml_buffer, uro_ifc_opening_attribute{}.uro_ifc_classification_reference_uro_name_codeSpace xml_buffer, uro_ifc_opening_attribute{}.uro_ifc_classification_reference_uro_reference_source_uro_ifc_classification_uro_source xml_buffer, uro_ifc_opening_attribute{}.uro_ifc_classification_reference_uro_reference_source_uro_ifc_classification_uro_edition xml_buffer,
      uro_ifc_opening_attribute{}.uro_ifc_classification_reference_uro_reference_source_uro_ifc_classification_uro_edition_date xml_date, uro_ifc_opening_attribute{}.uro_ifc_classification_reference_uro_reference_source_uro_ifc_classification_uro_name xml_buffer, uro_ifc_opening_attribute{}.uro_ifc_coordinate_reference_system_uro_name xml_buffer, uro_ifc_opening_attribute{}.uro_ifc_coordinate_reference_system_uro_description xml_buffer, uro_ifc_opening_attribute{}.uro_ifc_coordinate_reference_system_uro_geodetic_datum xml_buffer, uro_ifc_opening_attribute{}.uro_ifc_coordinate_reference_system_uro_vertical_datum xml_buffer, uro_ifc_opening_attribute{}.uro_ifc_curtain_wall_uro_global_id xml_buffer, uro_ifc_opening_attribute{}.uro_ifc_curtain_wall_uro_name xml_buffer, uro_ifc_opening_attribute{}.uro_ifc_curtain_wall_uro_description xml_buffer, uro_ifc_opening_attribute{}.uro_ifc_curtain_wall_uro_object_type xml_buffer, uro_ifc_opening_attribute{}.uro_ifc_curtain_wall_uro_tag xml_buffer, uro_ifc_opening_attribute{}.uro_ifc_curtain_wall_uro_element_type xml_buffer, uro_ifc_opening_attribute{}.uro_ifc_curtain_wall_uro_element_type_codeSpace xml_buffer, uro_ifc_opening_attribute{}.uro_ifc_curtain_wall_uro_predefined_type xml_buffer, uro_ifc_opening_attribute{}.uro_ifc_curtain_wall_uro_predefined_type_codeSpace xml_buffer, uro_ifc_opening_attribute{}.uro_ifc_curtain_wall_uro_shape_type xml_buffer, uro_ifc_opening_attribute{}.uro_ifc_curtain_wall_uro_shape_type_codeSpace xml_buffer, uro_ifc_opening_attribute{}.uro_ifc_curtain_wall_uro_number_of_riser xml_int64, uro_ifc_opening_attribute{}.uro_ifc_curtain_wall_uro_number_of_treads xml_int64, uro_ifc_opening_attribute{}.uro_ifc_curtain_wall_uro_riser_height xml_int64, uro_ifc_opening_attribute{}.uro_ifc_curtain_wall_uro_tread_length xml_int64, uro_ifc_opening_attribute{}.uro_ifc_curtain_wall_uro_operation_type xml_char(11), uro_ifc_opening_attribute{}.uro_ifc_curtain_wall_uro_capacity_by_weight xml_real64, uro_ifc_opening_attribute{}.uro_ifc_curtain_wall_uro_capacity_by_weight_units xml_buffer, uro_ifc_opening_attribute{}.uro_ifc_curtain_wall_uro_capacity_by_number xml_int64, uro_ifc_opening_attribute{}.uro_ifc_door_uro_global_id xml_buffer, uro_ifc_opening_attribute{}.uro_ifc_door_uro_name xml_buffer, uro_ifc_opening_attribute{}.uro_ifc_door_uro_description xml_buffer, uro_ifc_opening_attribute{}.uro_ifc_door_uro_object_type xml_buffer, uro_ifc_opening_attribute{}.uro_ifc_door_uro_tag xml_buffer,
      uro_ifc_opening_attribute{}.uro_ifc_door_uro_element_type xml_buffer, uro_ifc_opening_attribute{}.uro_ifc_door_uro_element_type_codeSpace xml_buffer, uro_ifc_opening_attribute{}.uro_ifc_door_uro_predefined_type xml_buffer, uro_ifc_opening_attribute{}.uro_ifc_door_uro_predefined_type_codeSpace xml_buffer, uro_ifc_opening_attribute{}.uro_ifc_door_uro_shape_type xml_buffer, uro_ifc_opening_attribute{}.uro_ifc_door_uro_shape_type_codeSpace xml_buffer, uro_ifc_opening_attribute{}.uro_ifc_door_uro_number_of_riser xml_int64, uro_ifc_opening_attribute{}.uro_ifc_door_uro_number_of_treads xml_int64, uro_ifc_opening_attribute{}.uro_ifc_door_uro_riser_height xml_int64, uro_ifc_opening_attribute{}.uro_ifc_door_uro_tread_length xml_int64, uro_ifc_opening_attribute{}.uro_ifc_door_uro_operation_type xml_char(11), uro_ifc_opening_attribute{}.uro_ifc_door_uro_capacity_by_weight xml_real64, uro_ifc_opening_attribute{}.uro_ifc_door_uro_capacity_by_weight_units xml_buffer, uro_ifc_opening_attribute{}.uro_ifc_door_uro_capacity_by_number xml_int64, uro_ifc_opening_attribute{}.uro_ifc_door_uro_overall_height xml_real64, uro_ifc_opening_attribute{}.uro_ifc_door_uro_overall_height_units xml_buffer, uro_ifc_opening_attribute{}.uro_ifc_door_uro_overall_width xml_real64, uro_ifc_opening_attribute{}.uro_ifc_door_uro_overall_width_units xml_buffer, uro_ifc_opening_attribute{}.uro_ifc_furnishing_element_uro_global_id xml_buffer, uro_ifc_opening_attribute{}.uro_ifc_furnishing_element_uro_name xml_buffer, uro_ifc_opening_attribute{}.uro_ifc_furnishing_element_uro_description xml_buffer, uro_ifc_opening_attribute{}.uro_ifc_furnishing_element_uro_object_type xml_buffer, uro_ifc_opening_attribute{}.uro_ifc_furnishing_element_uro_tag xml_buffer, uro_ifc_opening_attribute{}.uro_ifc_map_conversion_uro_source_crs_uro_crs_uro_ifc_projected_crs_uro_name xml_buffer, uro_ifc_opening_attribute{}.uro_ifc_map_conversion_uro_source_crs_uro_crs_uro_ifc_projected_crs_uro_description xml_buffer, uro_ifc_opening_attribute{}.uro_ifc_map_conversion_uro_source_crs_uro_crs_uro_ifc_projected_crs_uro_geodetic_datum xml_buffer, uro_ifc_opening_attribute{}.uro_ifc_map_conversion_uro_source_crs_uro_crs_uro_ifc_projected_crs_uro_vertical_datum xml_buffer, uro_ifc_opening_attribute{}.uro_ifc_map_conversion_uro_source_crs_uro_crs_uro_ifc_projected_crs_uro_map_unit xml_buffer, uro_ifc_opening_attribute{}.uro_ifc_map_conversion_uro_source_crs_uro_crs_uro_ifc_projected_crs_uro_map_projection xml_buffer, uro_ifc_opening_attribute{}.uro_ifc_map_conversion_uro_source_crs_uro_crs_uro_ifc_projected_crs_uro_map_zone xml_buffer,
      uro_ifc_opening_attribute{}.uro_ifc_map_conversion_uro_source_crs_uro_crs_uro_ifc_coordinate_reference_system_uro_name xml_buffer, uro_ifc_opening_attribute{}.uro_ifc_map_conversion_uro_source_crs_uro_crs_uro_ifc_coordinate_reference_system_uro_description xml_buffer, uro_ifc_opening_attribute{}.uro_ifc_map_conversion_uro_source_crs_uro_crs_uro_ifc_coordinate_reference_system_uro_geodetic_datum xml_buffer, uro_ifc_opening_attribute{}.uro_ifc_map_conversion_uro_source_crs_uro_crs_uro_ifc_coordinate_reference_system_uro_vertical_datum xml_buffer, uro_ifc_opening_attribute{}.uro_ifc_map_conversion_uro_source_crs_uro_context_uro_ifc_geometric_representation_context_uro_context_identifier xml_buffer, uro_ifc_opening_attribute{}.uro_ifc_map_conversion_uro_source_crs_uro_context_uro_ifc_geometric_representation_context_uro_context_type xml_buffer, uro_ifc_opening_attribute{}.uro_ifc_map_conversion_uro_source_crs_uro_context_uro_ifc_geometric_representation_context_uro_coordinate_space_dimension xml_int64, uro_ifc_opening_attribute{}.uro_ifc_map_conversion_uro_source_crs_uro_context_uro_ifc_geometric_representation_context_uro_precision xml_real64, uro_ifc_opening_attribute{}.uro_ifc_map_conversion_uro_source_crs_uro_context_uro_ifc_geometric_representation_context_uro_true_north xml_real64, uro_ifc_opening_attribute{}.uro_ifc_map_conversion_uro_target_crs_uro_ifc_projected_crs_uro_name xml_buffer, uro_ifc_opening_attribute{}.uro_ifc_map_conversion_uro_target_crs_uro_ifc_projected_crs_uro_description xml_buffer, uro_ifc_opening_attribute{}.uro_ifc_map_conversion_uro_target_crs_uro_ifc_projected_crs_uro_geodetic_datum xml_buffer, uro_ifc_opening_attribute{}.uro_ifc_map_conversion_uro_target_crs_uro_ifc_projected_crs_uro_vertical_datum xml_buffer, uro_ifc_opening_attribute{}.uro_ifc_map_conversion_uro_target_crs_uro_ifc_projected_crs_uro_map_unit xml_buffer, uro_ifc_opening_attribute{}.uro_ifc_map_conversion_uro_target_crs_uro_ifc_projected_crs_uro_map_projection xml_buffer, uro_ifc_opening_attribute{}.uro_ifc_map_conversion_uro_target_crs_uro_ifc_projected_crs_uro_map_zone xml_buffer, uro_ifc_opening_attribute{}.uro_ifc_map_conversion_uro_target_crs_uro_ifc_coordinate_reference_system_uro_name xml_buffer, uro_ifc_opening_attribute{}.uro_ifc_map_conversion_uro_target_crs_uro_ifc_coordinate_reference_system_uro_description xml_buffer, uro_ifc_opening_attribute{}.uro_ifc_map_conversion_uro_target_crs_uro_ifc_coordinate_reference_system_uro_geodetic_datum xml_buffer, uro_ifc_opening_attribute{}.uro_ifc_map_conversion_uro_target_crs_uro_ifc_coordinate_reference_system_uro_vertical_datum xml_buffer, uro_ifc_opening_attribute{}.uro_ifc_map_conversion_uro_eastings xml_buffer, uro_ifc_opening_attribute{}.uro_ifc_map_conversion_uro_northings xml_buffer, uro_ifc_opening_attribute{}.uro_ifc_map_conversion_uro_orthogonal_height xml_real64, uro_ifc_opening_attribute{}.uro_ifc_map_conversion_uro_orthogonal_height_units xml_buffer, uro_ifc_opening_attribute{}.uro_ifc_map_conversion_uro_x_axis_abscissa xml_real64, uro_ifc_opening_attribute{}.uro_ifc_map_conversion_uro_x_axis_ordinate xml_real64, uro_ifc_opening_attribute{}.uro_ifc_map_conversion_uro_scale xml_real64, uro_ifc_opening_attribute{}.uro_ifc_opening_element_uro_global_id xml_buffer, uro_ifc_opening_attribute{}.uro_ifc_opening_element_uro_name xml_buffer, uro_ifc_opening_attribute{}.uro_ifc_opening_element_uro_description xml_buffer,
      uro_ifc_opening_attribute{}.uro_ifc_opening_element_uro_object_type xml_buffer, uro_ifc_opening_attribute{}.uro_ifc_opening_element_uro_tag xml_buffer, uro_ifc_opening_attribute{}.uro_ifc_opening_element_uro_nominal_area xml_real64, uro_ifc_opening_attribute{}.uro_ifc_opening_element_uro_nominal_area_units xml_buffer, uro_ifc_opening_attribute{}.uro_ifc_opening_element_uro_nominal_volume xml_real64, uro_ifc_opening_attribute{}.uro_ifc_opening_element_uro_nominal_volume_units xml_buffer, uro_ifc_opening_attribute{}.uro_ifc_project_uro_global_id xml_buffer, uro_ifc_opening_attribute{}.uro_ifc_project_uro_name xml_buffer, uro_ifc_opening_attribute{}.uro_ifc_project_uro_description xml_buffer, uro_ifc_opening_attribute{}.uro_ifc_project_uro_object_type xml_buffer, uro_ifc_opening_attribute{}.uro_ifc_project_uro_long_name xml_buffer, uro_ifc_opening_attribute{}.uro_ifc_project_uro_phase xml_buffer, uro_ifc_opening_attribute{}.uro_ifc_project_uro_representation_contexts_uro_ifc_geometric_representation_context_uro_context_identifier xml_buffer, uro_ifc_opening_attribute{}.uro_ifc_project_uro_representation_contexts_uro_ifc_geometric_representation_context_uro_context_type xml_buffer, uro_ifc_opening_attribute{}.uro_ifc_project_uro_representation_contexts_uro_ifc_geometric_representation_context_uro_coordinate_space_dimension xml_int64, uro_ifc_opening_attribute{}.uro_ifc_project_uro_representation_contexts_uro_ifc_geometric_representation_context_uro_precision xml_real64, uro_ifc_opening_attribute{}.uro_ifc_project_uro_representation_contexts_uro_ifc_geometric_representation_context_uro_true_north xml_real64, uro_ifc_opening_attribute{}.uro_ifc_project_uro_units_in_context{}.uro_ifc_unit_uro_dimensions xml_int64, uro_ifc_opening_attribute{}.uro_ifc_project_uro_units_in_context{}.uro_ifc_unit_uro_unit_type xml_char(28), uro_ifc_opening_attribute{}.uro_ifc_project_uro_units_in_context{}.uro_ifc_unit_uro_perfix xml_buffer, uro_ifc_opening_attribute{}.uro_ifc_project_uro_units_in_context{}.uro_ifc_unit_uro_name xml_buffer, uro_ifc_opening_attribute{}.uro_ifc_projected_crs_uro_name xml_buffer, uro_ifc_opening_attribute{}.uro_ifc_projected_crs_uro_description xml_buffer, uro_ifc_opening_attribute{}.uro_ifc_projected_crs_uro_geodetic_datum xml_buffer, uro_ifc_opening_attribute{}.uro_ifc_projected_crs_uro_vertical_datum xml_buffer, uro_ifc_opening_attribute{}.uro_ifc_projected_crs_uro_map_unit xml_buffer, uro_ifc_opening_attribute{}.uro_ifc_projected_crs_uro_map_projection xml_buffer, uro_ifc_opening_attribute{}.uro_ifc_projected_crs_uro_map_zone xml_buffer, uro_ifc_opening_attribute{}.uro_ifc_pset_building_common_uro_building_id xml_real64, uro_ifc_opening_attribute{}.uro_ifc_pset_building_common_uro_building_id_units xml_buffer,
      uro_ifc_opening_attribute{}.uro_ifc_pset_building_common_uro_is_permanent_id xml_real64, uro_ifc_opening_attribute{}.uro_ifc_pset_building_common_uro_is_permanent_id_units xml_buffer, uro_ifc_opening_attribute{}.uro_ifc_pset_building_common_uro_main_fire_use xml_buffer, uro_ifc_opening_attribute{}.uro_ifc_pset_building_common_uro_ancillary_fire_use xml_buffer, uro_ifc_opening_attribute{}.uro_ifc_pset_building_common_uro_sprinkler_protection xml_boolean, uro_ifc_opening_attribute{}.uro_ifc_pset_building_common_uro_sprinkler_protection_automatic xml_boolean, uro_ifc_opening_attribute{}.uro_ifc_pset_building_common_uro_occupancy_type xml_buffer, uro_ifc_opening_attribute{}.uro_ifc_pset_building_common_uro_occupancy_type_codeSpace xml_buffer, uro_ifc_opening_attribute{}.uro_ifc_pset_building_common_uro_gross_planned_area xml_real64, uro_ifc_opening_attribute{}.uro_ifc_pset_building_common_uro_gross_planned_area_units xml_buffer, uro_ifc_opening_attribute{}.uro_ifc_pset_building_common_uro_number_of_storeys xml_int64, uro_ifc_opening_attribute{}.uro_ifc_pset_building_common_uro_year_of_construction xml_buffer, uro_ifc_opening_attribute{}.uro_ifc_pset_building_common_uro_is_landmarked xml_boolean, uro_ifc_opening_attribute{}.uro_ifc_pset_door_common_uro_reference xml_buffer, uro_ifc_opening_attribute{}.uro_ifc_pset_door_common_uro_acoustic_rating xml_buffer, uro_ifc_opening_attribute{}.uro_ifc_pset_door_common_uro_firerating xml_buffer, uro_ifc_opening_attribute{}.uro_ifc_pset_door_common_uro_security_rating xml_buffer, uro_ifc_opening_attribute{}.uro_ifc_pset_door_common_uro_is_external xml_boolean, uro_ifc_opening_attribute{}.uro_ifc_pset_door_common_uro_infiltration xml_real64, uro_ifc_opening_attribute{}.uro_ifc_pset_door_common_uro_thermal_transmittance xml_real64, uro_ifc_opening_attribute{}.uro_ifc_pset_door_common_uro_glazing_area_fraction xml_real64, uro_ifc_opening_attribute{}.uro_ifc_pset_door_common_uro_handicap_accessible xml_real64, uro_ifc_opening_attribute{}.uro_ifc_pset_door_common_uro_fire_exit xml_boolean, uro_ifc_opening_attribute{}.uro_ifc_pset_door_common_uro_self_closing xml_real64, uro_ifc_opening_attribute{}.uro_ifc_pset_door_common_uro_smoke_stop xml_boolean, uro_ifc_opening_attribute{}.uro_ifc_pset_opening_element_common_uro_reference xml_buffer, uro_ifc_opening_attribute{}.uro_ifc_pset_opening_element_common_uro_purpose xml_buffer, uro_ifc_opening_attribute{}.uro_ifc_pset_opening_element_common_uro_fire_exit xml_boolean, uro_ifc_opening_attribute{}.uro_ifc_pset_opening_element_common_uro_protected_opening xml_boolean, uro_ifc_opening_attribute{}.uro_ifc_pset_opening_element_common_uro_parallel_jambs xml_boolean,
      uro_ifc_opening_attribute{}.uro_ifc_pset_site_common_uro_buildable_area xml_real64, uro_ifc_opening_attribute{}.uro_ifc_pset_site_common_uro_buildable_area_units xml_buffer, uro_ifc_opening_attribute{}.uro_ifc_pset_site_common_uro_total_area xml_real64, uro_ifc_opening_attribute{}.uro_ifc_pset_site_common_uro_total_area_units xml_buffer, uro_ifc_opening_attribute{}.uro_ifc_pset_site_common_uro_building_height_limit xml_real64, uro_ifc_opening_attribute{}.uro_ifc_pset_site_common_uro_building_height_limit_units xml_buffer, uro_ifc_opening_attribute{}.uro_ifc_pset_space_common_uro_reference xml_buffer, uro_ifc_opening_attribute{}.uro_ifc_pset_space_common_uro_category xml_buffer, uro_ifc_opening_attribute{}.uro_ifc_pset_space_common_uro_category_codeSpace xml_buffer, uro_ifc_opening_attribute{}.uro_ifc_pset_space_common_uro_floor_covering xml_buffer, uro_ifc_opening_attribute{}.uro_ifc_pset_space_common_uro_wall_covering xml_buffer, uro_ifc_opening_attribute{}.uro_ifc_pset_space_common_uro_ceiling_covering xml_buffer, uro_ifc_opening_attribute{}.uro_ifc_pset_space_common_uro_skirting_covering xml_buffer, uro_ifc_opening_attribute{}.uro_ifc_pset_space_common_uro_gross_planned_area xml_real64, uro_ifc_opening_attribute{}.uro_ifc_pset_space_common_uro_gross_planned_area_units xml_buffer, uro_ifc_opening_attribute{}.uro_ifc_pset_space_common_uro_net_planned_area xml_real64, uro_ifc_opening_attribute{}.uro_ifc_pset_space_common_uro_net_planned_area_units xml_buffer, uro_ifc_opening_attribute{}.uro_ifc_pset_space_common_uro_publicly_accessible xml_boolean, uro_ifc_opening_attribute{}.uro_ifc_pset_space_common_uro_handicap_accessible xml_boolean, uro_ifc_opening_attribute{}.uro_ifc_pset_space_common_uro_concealed_flooring xml_boolean, uro_ifc_opening_attribute{}.uro_ifc_pset_space_common_uro_concealed_ceiling xml_boolean, uro_ifc_opening_attribute{}.uro_ifc_pset_window_common_uro_reference xml_buffer, uro_ifc_opening_attribute{}.uro_ifc_pset_window_common_uro_acoustic_rating xml_buffer, uro_ifc_opening_attribute{}.uro_ifc_pset_window_common_uro_firerating xml_buffer, uro_ifc_opening_attribute{}.uro_ifc_pset_window_common_uro_security_rating xml_buffer, uro_ifc_opening_attribute{}.uro_ifc_pset_window_common_uro_is_external xml_boolean, uro_ifc_opening_attribute{}.uro_ifc_pset_window_common_uro_infiltration xml_real64, uro_ifc_opening_attribute{}.uro_ifc_pset_window_common_uro_thermal_transmittance xml_real64, uro_ifc_opening_attribute{}.uro_ifc_pset_window_common_uro_glazing_area_fraction xml_real64, uro_ifc_opening_attribute{}.uro_ifc_pset_window_common_uro_smoke_stop xml_boolean,
      uro_ifc_opening_attribute{}.uro_ifc_site_uro_global_id xml_buffer, uro_ifc_opening_attribute{}.uro_ifc_site_uro_name xml_buffer, uro_ifc_opening_attribute{}.uro_ifc_site_uro_description xml_buffer, uro_ifc_opening_attribute{}.uro_ifc_site_uro_object_type xml_buffer, uro_ifc_opening_attribute{}.uro_ifc_site_uro_long_name xml_buffer, uro_ifc_opening_attribute{}.uro_ifc_site_uro_composition_type xml_char(7), uro_ifc_opening_attribute{}.uro_ifc_site_uro_ref_longitude xml_real64, uro_ifc_opening_attribute{}.uro_ifc_site_uro_ref_latitude xml_real64, uro_ifc_opening_attribute{}.uro_ifc_site_uro_ref_elevation xml_real64, uro_ifc_opening_attribute{}.uro_ifc_site_uro_ref_elevation_units xml_buffer, uro_ifc_opening_attribute{}.uro_ifc_site_uro_land_title_number xml_buffer, uro_ifc_opening_attribute{}.uro_ifc_site_uro_site_address_xlink_href xml_buffer, uro_ifc_opening_attribute{}.uro_ifc_space_uro_global_id xml_buffer, uro_ifc_opening_attribute{}.uro_ifc_space_uro_name xml_buffer, uro_ifc_opening_attribute{}.uro_ifc_space_uro_description xml_buffer, uro_ifc_opening_attribute{}.uro_ifc_space_uro_object_type xml_buffer, uro_ifc_opening_attribute{}.uro_ifc_space_uro_long_name xml_buffer, uro_ifc_opening_attribute{}.uro_ifc_space_uro_composition_type xml_char(7), uro_ifc_opening_attribute{}.uro_ifc_space_uro_interioror_exterior_space xml_char(10), uro_ifc_opening_attribute{}.uro_ifc_space_uro_elevation_with_flooring xml_real64, uro_ifc_opening_attribute{}.uro_ifc_space_uro_elevation_with_flooring_units xml_buffer, uro_ifc_opening_attribute{}.uro_ifc_space_base_quantity_uro_nominal_height xml_real64, uro_ifc_opening_attribute{}.uro_ifc_space_base_quantity_uro_nominal_height_units xml_buffer, uro_ifc_opening_attribute{}.uro_ifc_space_base_quantity_uro_clear_height xml_real64, uro_ifc_opening_attribute{}.uro_ifc_space_base_quantity_uro_clear_height_units xml_buffer, uro_ifc_opening_attribute{}.uro_ifc_space_base_quantity_uro_finish_ceiling_height xml_real64, uro_ifc_opening_attribute{}.uro_ifc_space_base_quantity_uro_finish_ceiling_height_units xml_buffer, uro_ifc_opening_attribute{}.uro_ifc_space_base_quantity_uro_gross_perimeter xml_real64, uro_ifc_opening_attribute{}.uro_ifc_space_base_quantity_uro_gross_perimeter_units xml_buffer, uro_ifc_opening_attribute{}.uro_ifc_space_base_quantity_uro_net_perimeter xml_real64,
      uro_ifc_opening_attribute{}.uro_ifc_space_base_quantity_uro_net_perimeter_units xml_buffer, uro_ifc_opening_attribute{}.uro_ifc_space_base_quantity_uro_gross_ceiling_area xml_real64, uro_ifc_opening_attribute{}.uro_ifc_space_base_quantity_uro_gross_ceiling_area_units xml_buffer, uro_ifc_opening_attribute{}.uro_ifc_space_base_quantity_uro_gross_floor_area xml_real64, uro_ifc_opening_attribute{}.uro_ifc_space_base_quantity_uro_gross_floor_area_units xml_buffer, uro_ifc_opening_attribute{}.uro_ifc_space_base_quantity_uro_net_ceiling_area xml_real64, uro_ifc_opening_attribute{}.uro_ifc_space_base_quantity_uro_net_ceiling_area_units xml_buffer, uro_ifc_opening_attribute{}.uro_ifc_space_base_quantity_uro_net_floor_area xml_real64, uro_ifc_opening_attribute{}.uro_ifc_space_base_quantity_uro_net_floor_area_units xml_buffer, uro_ifc_opening_attribute{}.uro_ifc_space_base_quantity_uro_gross_wall_area xml_real64, uro_ifc_opening_attribute{}.uro_ifc_space_base_quantity_uro_gross_wall_area_units xml_buffer, uro_ifc_opening_attribute{}.uro_ifc_space_base_quantity_uro_net_wall_area xml_real64, uro_ifc_opening_attribute{}.uro_ifc_space_base_quantity_uro_net_wall_area_units xml_buffer, uro_ifc_opening_attribute{}.uro_ifc_space_base_quantity_uro_gross_volume xml_real64, uro_ifc_opening_attribute{}.uro_ifc_space_base_quantity_uro_gross_volume_units xml_buffer, uro_ifc_opening_attribute{}.uro_ifc_space_base_quantity_uro_net_volume xml_real64, uro_ifc_opening_attribute{}.uro_ifc_space_base_quantity_uro_net_volume_units xml_buffer, uro_ifc_opening_attribute{}.uro_ifc_wall_uro_global_id xml_buffer, uro_ifc_opening_attribute{}.uro_ifc_wall_uro_name xml_buffer, uro_ifc_opening_attribute{}.uro_ifc_wall_uro_description xml_buffer, uro_ifc_opening_attribute{}.uro_ifc_wall_uro_object_type xml_buffer, uro_ifc_opening_attribute{}.uro_ifc_wall_uro_tag xml_buffer, uro_ifc_opening_attribute{}.uro_ifc_wall_uro_element_type xml_buffer, uro_ifc_opening_attribute{}.uro_ifc_wall_uro_element_type_codeSpace xml_buffer, uro_ifc_opening_attribute{}.uro_ifc_wall_uro_predefined_type xml_buffer, uro_ifc_opening_attribute{}.uro_ifc_wall_uro_predefined_type_codeSpace xml_buffer, uro_ifc_opening_attribute{}.uro_ifc_wall_uro_shape_type xml_buffer, uro_ifc_opening_attribute{}.uro_ifc_wall_uro_shape_type_codeSpace xml_buffer, uro_ifc_opening_attribute{}.uro_ifc_wall_uro_number_of_riser xml_int64, uro_ifc_opening_attribute{}.uro_ifc_wall_uro_number_of_treads xml_int64,
      uro_ifc_opening_attribute{}.uro_ifc_wall_uro_riser_height xml_int64, uro_ifc_opening_attribute{}.uro_ifc_wall_uro_tread_length xml_int64, uro_ifc_opening_attribute{}.uro_ifc_wall_uro_operation_type xml_char(11), uro_ifc_opening_attribute{}.uro_ifc_wall_uro_capacity_by_weight xml_real64, uro_ifc_opening_attribute{}.uro_ifc_wall_uro_capacity_by_weight_units xml_buffer, uro_ifc_opening_attribute{}.uro_ifc_wall_uro_capacity_by_number xml_int64, uro_ifc_opening_attribute{}.uro_ifc_wall_uro_nominal_length xml_real64, uro_ifc_opening_attribute{}.uro_ifc_wall_uro_nominal_length_units xml_buffer, uro_ifc_opening_attribute{}.uro_ifc_wall_uro_nominal_width xml_real64, uro_ifc_opening_attribute{}.uro_ifc_wall_uro_nominal_width_units xml_buffer, uro_ifc_opening_attribute{}.uro_ifc_wall_uro_nominal_height xml_real64, uro_ifc_opening_attribute{}.uro_ifc_wall_uro_nominal_height_units xml_buffer, uro_ifc_opening_attribute{}.uro_ifc_wall_uro_gross_foot_print_area xml_real64, uro_ifc_opening_attribute{}.uro_ifc_wall_uro_gross_foot_print_area_units xml_buffer, uro_ifc_opening_attribute{}.uro_ifc_wall_uro_net_foot_print_area xml_real64, uro_ifc_opening_attribute{}.uro_ifc_wall_uro_net_foot_print_area_units xml_buffer, uro_ifc_opening_attribute{}.uro_ifc_wall_uro_gross_side_area xml_real64, uro_ifc_opening_attribute{}.uro_ifc_wall_uro_gross_side_area_units xml_buffer, uro_ifc_opening_attribute{}.uro_ifc_wall_uro_net_side_area xml_real64, uro_ifc_opening_attribute{}.uro_ifc_wall_uro_net_side_area_units xml_buffer, uro_ifc_opening_attribute{}.uro_ifc_wall_uro_gross_side_area_left xml_real64, uro_ifc_opening_attribute{}.uro_ifc_wall_uro_gross_side_area_left_units xml_buffer, uro_ifc_opening_attribute{}.uro_ifc_wall_uro_net_side_area_left xml_real64, uro_ifc_opening_attribute{}.uro_ifc_wall_uro_net_side_area_left_units xml_buffer, uro_ifc_opening_attribute{}.uro_ifc_wall_uro_gross_side_area_right xml_real64, uro_ifc_opening_attribute{}.uro_ifc_wall_uro_gross_side_area_right_units xml_buffer, uro_ifc_opening_attribute{}.uro_ifc_wall_uro_net_side_area_right xml_real64, uro_ifc_opening_attribute{}.uro_ifc_wall_uro_net_side_area_right_units xml_buffer, uro_ifc_opening_attribute{}.uro_ifc_wall_uro_gross_volume xml_real64, uro_ifc_opening_attribute{}.uro_ifc_wall_uro_gross_volume_units xml_buffer,
      uro_ifc_opening_attribute{}.uro_ifc_wall_uro_net_volume xml_real64, uro_ifc_opening_attribute{}.uro_ifc_wall_uro_net_volume_units xml_buffer, uro_ifc_opening_attribute{}.uro_ifc_wall_standard_case_uro_global_id xml_buffer, uro_ifc_opening_attribute{}.uro_ifc_wall_standard_case_uro_name xml_buffer, uro_ifc_opening_attribute{}.uro_ifc_wall_standard_case_uro_description xml_buffer, uro_ifc_opening_attribute{}.uro_ifc_wall_standard_case_uro_object_type xml_buffer, uro_ifc_opening_attribute{}.uro_ifc_wall_standard_case_uro_tag xml_buffer, uro_ifc_opening_attribute{}.uro_ifc_wall_standard_case_uro_element_type xml_buffer, uro_ifc_opening_attribute{}.uro_ifc_wall_standard_case_uro_element_type_codeSpace xml_buffer, uro_ifc_opening_attribute{}.uro_ifc_wall_standard_case_uro_predefined_type xml_buffer, uro_ifc_opening_attribute{}.uro_ifc_wall_standard_case_uro_predefined_type_codeSpace xml_buffer, uro_ifc_opening_attribute{}.uro_ifc_wall_standard_case_uro_shape_type xml_buffer, uro_ifc_opening_attribute{}.uro_ifc_wall_standard_case_uro_shape_type_codeSpace xml_buffer, uro_ifc_opening_attribute{}.uro_ifc_wall_standard_case_uro_number_of_riser xml_int64, uro_ifc_opening_attribute{}.uro_ifc_wall_standard_case_uro_number_of_treads xml_int64, uro_ifc_opening_attribute{}.uro_ifc_wall_standard_case_uro_riser_height xml_int64, uro_ifc_opening_attribute{}.uro_ifc_wall_standard_case_uro_tread_length xml_int64, uro_ifc_opening_attribute{}.uro_ifc_wall_standard_case_uro_operation_type xml_char(11), uro_ifc_opening_attribute{}.uro_ifc_wall_standard_case_uro_capacity_by_weight xml_real64, uro_ifc_opening_attribute{}.uro_ifc_wall_standard_case_uro_capacity_by_weight_units xml_buffer, uro_ifc_opening_attribute{}.uro_ifc_wall_standard_case_uro_capacity_by_number xml_int64, uro_ifc_opening_attribute{}.uro_ifc_wall_standard_case_uro_nominal_length xml_real64, uro_ifc_opening_attribute{}.uro_ifc_wall_standard_case_uro_nominal_length_units xml_buffer, uro_ifc_opening_attribute{}.uro_ifc_wall_standard_case_uro_nominal_width xml_real64, uro_ifc_opening_attribute{}.uro_ifc_wall_standard_case_uro_nominal_width_units xml_buffer, uro_ifc_opening_attribute{}.uro_ifc_wall_standard_case_uro_nominal_height xml_real64, uro_ifc_opening_attribute{}.uro_ifc_wall_standard_case_uro_nominal_height_units xml_buffer, uro_ifc_opening_attribute{}.uro_ifc_wall_standard_case_uro_gross_foot_print_area xml_real64, uro_ifc_opening_attribute{}.uro_ifc_wall_standard_case_uro_gross_foot_print_area_units xml_buffer, uro_ifc_opening_attribute{}.uro_ifc_wall_standard_case_uro_net_foot_print_area xml_real64,
      uro_ifc_opening_attribute{}.uro_ifc_wall_standard_case_uro_net_foot_print_area_units xml_buffer, uro_ifc_opening_attribute{}.uro_ifc_wall_standard_case_uro_gross_side_area xml_real64, uro_ifc_opening_attribute{}.uro_ifc_wall_standard_case_uro_gross_side_area_units xml_buffer, uro_ifc_opening_attribute{}.uro_ifc_wall_standard_case_uro_net_side_area xml_real64, uro_ifc_opening_attribute{}.uro_ifc_wall_standard_case_uro_net_side_area_units xml_buffer, uro_ifc_opening_attribute{}.uro_ifc_wall_standard_case_uro_gross_side_area_left xml_real64, uro_ifc_opening_attribute{}.uro_ifc_wall_standard_case_uro_gross_side_area_left_units xml_buffer, uro_ifc_opening_attribute{}.uro_ifc_wall_standard_case_uro_net_side_area_left xml_real64, uro_ifc_opening_attribute{}.uro_ifc_wall_standard_case_uro_net_side_area_left_units xml_buffer, uro_ifc_opening_attribute{}.uro_ifc_wall_standard_case_uro_gross_side_area_right xml_real64, uro_ifc_opening_attribute{}.uro_ifc_wall_standard_case_uro_gross_side_area_right_units xml_buffer, uro_ifc_opening_attribute{}.uro_ifc_wall_standard_case_uro_net_side_area_right xml_real64, uro_ifc_opening_attribute{}.uro_ifc_wall_standard_case_uro_net_side_area_right_units xml_buffer, uro_ifc_opening_attribute{}.uro_ifc_wall_standard_case_uro_gross_volume xml_real64, uro_ifc_opening_attribute{}.uro_ifc_wall_standard_case_uro_gross_volume_units xml_buffer, uro_ifc_opening_attribute{}.uro_ifc_wall_standard_case_uro_net_volume xml_real64, uro_ifc_opening_attribute{}.uro_ifc_wall_standard_case_uro_net_volume_units xml_buffer, uro_ifc_opening_attribute{}.uro_ifc_window_uro_global_id xml_buffer, uro_ifc_opening_attribute{}.uro_ifc_window_uro_name xml_buffer, uro_ifc_opening_attribute{}.uro_ifc_window_uro_description xml_buffer, uro_ifc_opening_attribute{}.uro_ifc_window_uro_object_type xml_buffer, uro_ifc_opening_attribute{}.uro_ifc_window_uro_tag xml_buffer, uro_ifc_opening_attribute{}.uro_ifc_window_uro_element_type xml_buffer, uro_ifc_opening_attribute{}.uro_ifc_window_uro_element_type_codeSpace xml_buffer, uro_ifc_opening_attribute{}.uro_ifc_window_uro_predefined_type xml_buffer, uro_ifc_opening_attribute{}.uro_ifc_window_uro_predefined_type_codeSpace xml_buffer, uro_ifc_opening_attribute{}.uro_ifc_window_uro_shape_type xml_buffer, uro_ifc_opening_attribute{}.uro_ifc_window_uro_shape_type_codeSpace xml_buffer, uro_ifc_opening_attribute{}.uro_ifc_window_uro_number_of_riser xml_int64, uro_ifc_opening_attribute{}.uro_ifc_window_uro_number_of_treads xml_int64,
      uro_ifc_opening_attribute{}.uro_ifc_window_uro_riser_height xml_int64, uro_ifc_opening_attribute{}.uro_ifc_window_uro_tread_length xml_int64, uro_ifc_opening_attribute{}.uro_ifc_window_uro_operation_type xml_char(11), uro_ifc_opening_attribute{}.uro_ifc_window_uro_capacity_by_weight xml_real64, uro_ifc_opening_attribute{}.uro_ifc_window_uro_capacity_by_weight_units xml_buffer, uro_ifc_opening_attribute{}.uro_ifc_window_uro_capacity_by_number xml_int64, uro_ifc_opening_attribute{}.uro_ifc_window_uro_overall_height xml_real64, uro_ifc_opening_attribute{}.uro_ifc_window_uro_overall_height_units xml_buffer, uro_ifc_opening_attribute{}.uro_ifc_window_uro_overall_width xml_real64, uro_ifc_opening_attribute{}.uro_ifc_window_uro_overall_width_units xml_buffer
Note: AttributeManager_13 : Input / Room ソリッドに集約
Junction_24
    -> Junction_25
Note: interior Window, Door / AttributeManager_11 : Output
Junction_25
    -> AttributeManager_13
TestFilter_4
    DEFAULT_VALUE = InteriorWall
    PASSED_TEST_GROUP_OUTPUT = FIRST
    TEST_LIST = "BOOL_OP,OR,COMPOSITE_TEST,""""""1"""""",TEST_CLAUSE,TEST @Value(_surfaceNormalZ) < -0.5",CeilingSurface,"BOOL_OP,OR,COMPOSITE_TEST,""""""1"""""",TEST_CLAUSE,TEST 0.5 < @Value(_surfaceNormalZ)",FloorSurface
    CeilingSurface -> Clipper_5 [CANDIDATE]
    FloorSurface -> Clipper_6 [CANDIDATE]
    InteriorWall -> Junction_80
Junction_79
    -> AttributeManager_3
Note: 屋内開口部: ClosureSurface
AttributeManager_3
    ATTR_TABLE:
      SET_TO gml_id = open_@UUID()
      SET_TO _citygml_feature_type = ClosureSurface
      REMOVE _surfaceNormalX
      REMOVE _surfaceNormalY
      REMOVE _surfaceNormalZ
      REMOVE _pointOnSurfaceX
      REMOVE _pointOnSurfaceY
      REMOVE _pointOnSurfaceZ
      REMOVE _clipped
      SET_TO citygml_lod_name = lod4MultiSurface
      SET_TO citygml_feature_role = boundedBy
    -> GeometryPropertySetter_15
    -> Junction_8
GeometryPropertySetter_15
    GQUERY:
      for $geom in //geometry
      where $geom/count(parent::geometry) = 0
      return number($geom/@fme_id)
    OVERWRITE_CHOICE = Yes
    REMOVE_ATTRIBUTE = Yes
    SETTYPE_PARAM = Traits From Attributes
    SRC_ATTRS = citygml_lod_name gml_id
    SET -> AttributeCreator_18
AttributeCreator_18
    ATTR_TABLE:
      SET_TO gml_id = bdry_@UUID()
      SET_TO gml_parent_id = @Value(_room_gml_id)
    -> PLATEAU.IfcReprojector_12 [IfcFeature]
PLATEAU.IfcReprojector_12
    DEST_COORDSYS = $(DEST_COORDSYS)
    LENGTH_MULTIPLIER = @Value(_lengthmultiplier)
    REPROJECTION_PARAMS = @Value(_reprojection_params)
    Reprojected -> ClosureSurface (writer CITYGML_2)
ClosureSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, uro_ifc_boundary_surface_attribute{}.uro_ifc_building_uro_global_id xml_buffer, uro_ifc_boundary_surface_attribute{}.uro_ifc_building_uro_name xml_buffer, uro_ifc_boundary_surface_attribute{}.uro_ifc_building_uro_description xml_buffer, uro_ifc_boundary_surface_attribute{}.uro_ifc_building_uro_object_type xml_buffer, uro_ifc_boundary_surface_attribute{}.uro_ifc_building_uro_long_name xml_buffer, uro_ifc_boundary_surface_attribute{}.uro_ifc_building_uro_composition_type xml_char(7), uro_ifc_boundary_surface_attribute{}.uro_ifc_building_uro_elevation_of_ref_height xml_real64, uro_ifc_boundary_surface_attribute{}.uro_ifc_building_uro_elevation_of_ref_height_units xml_buffer, uro_ifc_boundary_surface_attribute{}.uro_ifc_building_uro_elevation_of_terrain xml_real64, uro_ifc_boundary_surface_attribute{}.uro_ifc_building_uro_elevation_of_terrain_units xml_buffer, uro_ifc_boundary_surface_attribute{}.uro_ifc_building_uro_building_address_xlink_href xml_buffer, uro_ifc_boundary_surface_attribute{}.uro_ifc_building_element_uro_global_id xml_buffer, uro_ifc_boundary_surface_attribute{}.uro_ifc_building_element_uro_name xml_buffer, uro_ifc_boundary_surface_attribute{}.uro_ifc_building_element_uro_description xml_buffer,
      uro_ifc_boundary_surface_attribute{}.uro_ifc_building_element_uro_object_type xml_buffer, uro_ifc_boundary_surface_attribute{}.uro_ifc_building_element_uro_tag xml_buffer, uro_ifc_boundary_surface_attribute{}.uro_ifc_building_element_uro_element_type xml_buffer, uro_ifc_boundary_surface_attribute{}.uro_ifc_building_element_uro_element_type_codeSpace xml_buffer, uro_ifc_boundary_surface_attribute{}.uro_ifc_building_element_uro_predefined_type xml_buffer, uro_ifc_boundary_surface_attribute{}.uro_ifc_building_element_uro_predefined_type_codeSpace xml_buffer, uro_ifc_boundary_surface_attribute{}.uro_ifc_building_element_uro_shape_type xml_buffer, uro_ifc_boundary_surface_attribute{}.uro_ifc_building_element_uro_shape_type_codeSpace xml_buffer, uro_ifc_boundary_surface_attribute{}.uro_ifc_building_element_uro_number_of_riser xml_int64, uro_ifc_boundary_surface_attribute{}.uro_ifc_building_element_uro_number_of_treads xml_int64, uro_ifc_boundary_surface_attribute{}.uro_ifc_building_element_uro_riser_height xml_int64, uro_ifc_boundary_surface_attribute{}.uro_ifc_building_element_uro_tread_length xml_int64, uro_ifc_boundary_surface_attribute{}.uro_ifc_building_element_uro_operation_type xml_char(11), uro_ifc_boundary_surface_attribute{}.uro_ifc_building_element_uro_capacity_by_weight xml_real64, uro_ifc_boundary_surface_attribute{}.uro_ifc_building_element_uro_capacity_by_weight_units xml_buffer, uro_ifc_boundary_surface_attribute{}.uro_ifc_building_element_uro_capacity_by_number xml_int64, uro_ifc_boundary_surface_attribute{}.uro_ifc_building_storey_uro_global_id xml_buffer, uro_ifc_boundary_surface_attribute{}.uro_ifc_building_storey_uro_name xml_buffer, uro_ifc_boundary_surface_attribute{}.uro_ifc_building_storey_uro_description xml_buffer, uro_ifc_boundary_surface_attribute{}.uro_ifc_building_storey_uro_object_type xml_buffer, uro_ifc_boundary_surface_attribute{}.uro_ifc_building_storey_uro_long_name xml_buffer, uro_ifc_boundary_surface_attribute{}.uro_ifc_building_storey_uro_composition_type xml_char(7), uro_ifc_boundary_surface_attribute{}.uro_ifc_building_storey_uro_elevation xml_real64, uro_ifc_boundary_surface_attribute{}.uro_ifc_building_storey_uro_elevation_units xml_buffer, uro_ifc_boundary_surface_attribute{}.uro_ifc_classification_reference_uro_location xml_buffer, uro_ifc_boundary_surface_attribute{}.uro_ifc_classification_reference_uro_item_reference xml_buffer, uro_ifc_boundary_surface_attribute{}.uro_ifc_classification_reference_uro_item_reference_codeSpace xml_buffer, uro_ifc_boundary_surface_attribute{}.uro_ifc_classification_reference_uro_name xml_buffer, uro_ifc_boundary_surface_attribute{}.uro_ifc_classification_reference_uro_name_codeSpace xml_buffer, uro_ifc_boundary_surface_attribute{}.uro_ifc_classification_reference_uro_reference_source_uro_ifc_classification_uro_source xml_buffer,
      uro_ifc_boundary_surface_attribute{}.uro_ifc_classification_reference_uro_reference_source_uro_ifc_classification_uro_edition xml_buffer, uro_ifc_boundary_surface_attribute{}.uro_ifc_classification_reference_uro_reference_source_uro_ifc_classification_uro_edition_date xml_date, uro_ifc_boundary_surface_attribute{}.uro_ifc_classification_reference_uro_reference_source_uro_ifc_classification_uro_name xml_buffer, uro_ifc_boundary_surface_attribute{}.uro_ifc_coordinate_reference_system_uro_name xml_buffer, uro_ifc_boundary_surface_attribute{}.uro_ifc_coordinate_reference_system_uro_description xml_buffer, uro_ifc_boundary_surface_attribute{}.uro_ifc_coordinate_reference_system_uro_geodetic_datum xml_buffer, uro_ifc_boundary_surface_attribute{}.uro_ifc_coordinate_reference_system_uro_vertical_datum xml_buffer, uro_ifc_boundary_surface_attribute{}.uro_ifc_curtain_wall_uro_global_id xml_buffer, uro_ifc_boundary_surface_attribute{}.uro_ifc_curtain_wall_uro_name xml_buffer, uro_ifc_boundary_surface_attribute{}.uro_ifc_curtain_wall_uro_description xml_buffer, uro_ifc_boundary_surface_attribute{}.uro_ifc_curtain_wall_uro_object_type xml_buffer, uro_ifc_boundary_surface_attribute{}.uro_ifc_curtain_wall_uro_tag xml_buffer, uro_ifc_boundary_surface_attribute{}.uro_ifc_curtain_wall_uro_element_type xml_buffer, uro_ifc_boundary_surface_attribute{}.uro_ifc_curtain_wall_uro_element_type_codeSpace xml_buffer, uro_ifc_boundary_surface_attribute{}.uro_ifc_curtain_wall_uro_predefined_type xml_buffer, uro_ifc_boundary_surface_attribute{}.uro_ifc_curtain_wall_uro_predefined_type_codeSpace xml_buffer, uro_ifc_boundary_surface_attribute{}.uro_ifc_curtain_wall_uro_shape_type xml_buffer, uro_ifc_boundary_surface_attribute{}.uro_ifc_curtain_wall_uro_shape_type_codeSpace xml_buffer, uro_ifc_boundary_surface_attribute{}.uro_ifc_curtain_wall_uro_number_of_riser xml_int64, uro_ifc_boundary_surface_attribute{}.uro_ifc_curtain_wall_uro_number_of_treads xml_int64, uro_ifc_boundary_surface_attribute{}.uro_ifc_curtain_wall_uro_riser_height xml_int64, uro_ifc_boundary_surface_attribute{}.uro_ifc_curtain_wall_uro_tread_length xml_int64, uro_ifc_boundary_surface_attribute{}.uro_ifc_curtain_wall_uro_operation_type xml_char(11), uro_ifc_boundary_surface_attribute{}.uro_ifc_curtain_wall_uro_capacity_by_weight xml_real64, uro_ifc_boundary_surface_attribute{}.uro_ifc_curtain_wall_uro_capacity_by_weight_units xml_buffer, uro_ifc_boundary_surface_attribute{}.uro_ifc_curtain_wall_uro_capacity_by_number xml_int64, uro_ifc_boundary_surface_attribute{}.uro_ifc_door_uro_global_id xml_buffer, uro_ifc_boundary_surface_attribute{}.uro_ifc_door_uro_name xml_buffer, uro_ifc_boundary_surface_attribute{}.uro_ifc_door_uro_description xml_buffer, uro_ifc_boundary_surface_attribute{}.uro_ifc_door_uro_object_type xml_buffer,
      uro_ifc_boundary_surface_attribute{}.uro_ifc_door_uro_tag xml_buffer, uro_ifc_boundary_surface_attribute{}.uro_ifc_door_uro_element_type xml_buffer, uro_ifc_boundary_surface_attribute{}.uro_ifc_door_uro_element_type_codeSpace xml_buffer, uro_ifc_boundary_surface_attribute{}.uro_ifc_door_uro_predefined_type xml_buffer, uro_ifc_boundary_surface_attribute{}.uro_ifc_door_uro_predefined_type_codeSpace xml_buffer, uro_ifc_boundary_surface_attribute{}.uro_ifc_door_uro_shape_type xml_buffer, uro_ifc_boundary_surface_attribute{}.uro_ifc_door_uro_shape_type_codeSpace xml_buffer, uro_ifc_boundary_surface_attribute{}.uro_ifc_door_uro_number_of_riser xml_int64, uro_ifc_boundary_surface_attribute{}.uro_ifc_door_uro_number_of_treads xml_int64, uro_ifc_boundary_surface_attribute{}.uro_ifc_door_uro_riser_height xml_int64, uro_ifc_boundary_surface_attribute{}.uro_ifc_door_uro_tread_length xml_int64, uro_ifc_boundary_surface_attribute{}.uro_ifc_door_uro_operation_type xml_char(11), uro_ifc_boundary_surface_attribute{}.uro_ifc_door_uro_capacity_by_weight xml_real64, uro_ifc_boundary_surface_attribute{}.uro_ifc_door_uro_capacity_by_weight_units xml_buffer, uro_ifc_boundary_surface_attribute{}.uro_ifc_door_uro_capacity_by_number xml_int64, uro_ifc_boundary_surface_attribute{}.uro_ifc_door_uro_overall_height xml_real64, uro_ifc_boundary_surface_attribute{}.uro_ifc_door_uro_overall_height_units xml_buffer, uro_ifc_boundary_surface_attribute{}.uro_ifc_door_uro_overall_width xml_real64, uro_ifc_boundary_surface_attribute{}.uro_ifc_door_uro_overall_width_units xml_buffer, uro_ifc_boundary_surface_attribute{}.uro_ifc_furnishing_element_uro_global_id xml_buffer, uro_ifc_boundary_surface_attribute{}.uro_ifc_furnishing_element_uro_name xml_buffer, uro_ifc_boundary_surface_attribute{}.uro_ifc_furnishing_element_uro_description xml_buffer, uro_ifc_boundary_surface_attribute{}.uro_ifc_furnishing_element_uro_object_type xml_buffer, uro_ifc_boundary_surface_attribute{}.uro_ifc_furnishing_element_uro_tag xml_buffer, uro_ifc_boundary_surface_attribute{}.uro_ifc_map_conversion_uro_source_crs_uro_crs_uro_ifc_projected_crs_uro_name xml_buffer, uro_ifc_boundary_surface_attribute{}.uro_ifc_map_conversion_uro_source_crs_uro_crs_uro_ifc_projected_crs_uro_description xml_buffer, uro_ifc_boundary_surface_attribute{}.uro_ifc_map_conversion_uro_source_crs_uro_crs_uro_ifc_projected_crs_uro_geodetic_datum xml_buffer, uro_ifc_boundary_surface_attribute{}.uro_ifc_map_conversion_uro_source_crs_uro_crs_uro_ifc_projected_crs_uro_vertical_datum xml_buffer, uro_ifc_boundary_surface_attribute{}.uro_ifc_map_conversion_uro_source_crs_uro_crs_uro_ifc_projected_crs_uro_map_unit xml_buffer, uro_ifc_boundary_surface_attribute{}.uro_ifc_map_conversion_uro_source_crs_uro_crs_uro_ifc_projected_crs_uro_map_projection xml_buffer,
      uro_ifc_boundary_surface_attribute{}.uro_ifc_map_conversion_uro_source_crs_uro_crs_uro_ifc_projected_crs_uro_map_zone xml_buffer, uro_ifc_boundary_surface_attribute{}.uro_ifc_map_conversion_uro_source_crs_uro_crs_uro_ifc_coordinate_reference_system_uro_name xml_buffer, uro_ifc_boundary_surface_attribute{}.uro_ifc_map_conversion_uro_source_crs_uro_crs_uro_ifc_coordinate_reference_system_uro_description xml_buffer, uro_ifc_boundary_surface_attribute{}.uro_ifc_map_conversion_uro_source_crs_uro_crs_uro_ifc_coordinate_reference_system_uro_geodetic_datum xml_buffer, uro_ifc_boundary_surface_attribute{}.uro_ifc_map_conversion_uro_source_crs_uro_crs_uro_ifc_coordinate_reference_system_uro_vertical_datum xml_buffer, uro_ifc_boundary_surface_attribute{}.uro_ifc_map_conversion_uro_source_crs_uro_context_uro_ifc_geometric_representation_context_uro_context_identifier xml_buffer, uro_ifc_boundary_surface_attribute{}.uro_ifc_map_conversion_uro_source_crs_uro_context_uro_ifc_geometric_representation_context_uro_context_type xml_buffer, uro_ifc_boundary_surface_attribute{}.uro_ifc_map_conversion_uro_source_crs_uro_context_uro_ifc_geometric_representation_context_uro_coordinate_space_dimension xml_int64, uro_ifc_boundary_surface_attribute{}.uro_ifc_map_conversion_uro_source_crs_uro_context_uro_ifc_geometric_representation_context_uro_precision xml_real64, uro_ifc_boundary_surface_attribute{}.uro_ifc_map_conversion_uro_source_crs_uro_context_uro_ifc_geometric_representation_context_uro_true_north xml_real64, uro_ifc_boundary_surface_attribute{}.uro_ifc_map_conversion_uro_target_crs_uro_ifc_projected_crs_uro_name xml_buffer, uro_ifc_boundary_surface_attribute{}.uro_ifc_map_conversion_uro_target_crs_uro_ifc_projected_crs_uro_description xml_buffer, uro_ifc_boundary_surface_attribute{}.uro_ifc_map_conversion_uro_target_crs_uro_ifc_projected_crs_uro_geodetic_datum xml_buffer, uro_ifc_boundary_surface_attribute{}.uro_ifc_map_conversion_uro_target_crs_uro_ifc_projected_crs_uro_vertical_datum xml_buffer, uro_ifc_boundary_surface_attribute{}.uro_ifc_map_conversion_uro_target_crs_uro_ifc_projected_crs_uro_map_unit xml_buffer, uro_ifc_boundary_surface_attribute{}.uro_ifc_map_conversion_uro_target_crs_uro_ifc_projected_crs_uro_map_projection xml_buffer, uro_ifc_boundary_surface_attribute{}.uro_ifc_map_conversion_uro_target_crs_uro_ifc_projected_crs_uro_map_zone xml_buffer, uro_ifc_boundary_surface_attribute{}.uro_ifc_map_conversion_uro_target_crs_uro_ifc_coordinate_reference_system_uro_name xml_buffer, uro_ifc_boundary_surface_attribute{}.uro_ifc_map_conversion_uro_target_crs_uro_ifc_coordinate_reference_system_uro_description xml_buffer, uro_ifc_boundary_surface_attribute{}.uro_ifc_map_conversion_uro_target_crs_uro_ifc_coordinate_reference_system_uro_geodetic_datum xml_buffer, uro_ifc_boundary_surface_attribute{}.uro_ifc_map_conversion_uro_target_crs_uro_ifc_coordinate_reference_system_uro_vertical_datum xml_buffer, uro_ifc_boundary_surface_attribute{}.uro_ifc_map_conversion_uro_eastings xml_buffer, uro_ifc_boundary_surface_attribute{}.uro_ifc_map_conversion_uro_northings xml_buffer, uro_ifc_boundary_surface_attribute{}.uro_ifc_map_conversion_uro_orthogonal_height xml_real64, uro_ifc_boundary_surface_attribute{}.uro_ifc_map_conversion_uro_orthogonal_height_units xml_buffer, uro_ifc_boundary_surface_attribute{}.uro_ifc_map_conversion_uro_x_axis_abscissa xml_real64, uro_ifc_boundary_surface_attribute{}.uro_ifc_map_conversion_uro_x_axis_ordinate xml_real64, uro_ifc_boundary_surface_attribute{}.uro_ifc_map_conversion_uro_scale xml_real64, uro_ifc_boundary_surface_attribute{}.uro_ifc_opening_element_uro_global_id xml_buffer, uro_ifc_boundary_surface_attribute{}.uro_ifc_opening_element_uro_name xml_buffer,
      uro_ifc_boundary_surface_attribute{}.uro_ifc_opening_element_uro_description xml_buffer, uro_ifc_boundary_surface_attribute{}.uro_ifc_opening_element_uro_object_type xml_buffer, uro_ifc_boundary_surface_attribute{}.uro_ifc_opening_element_uro_tag xml_buffer, uro_ifc_boundary_surface_attribute{}.uro_ifc_opening_element_uro_nominal_area xml_real64, uro_ifc_boundary_surface_attribute{}.uro_ifc_opening_element_uro_nominal_area_units xml_buffer, uro_ifc_boundary_surface_attribute{}.uro_ifc_opening_element_uro_nominal_volume xml_real64, uro_ifc_boundary_surface_attribute{}.uro_ifc_opening_element_uro_nominal_volume_units xml_buffer, uro_ifc_boundary_surface_attribute{}.uro_ifc_project_uro_global_id xml_buffer, uro_ifc_boundary_surface_attribute{}.uro_ifc_project_uro_name xml_buffer, uro_ifc_boundary_surface_attribute{}.uro_ifc_project_uro_description xml_buffer, uro_ifc_boundary_surface_attribute{}.uro_ifc_project_uro_object_type xml_buffer, uro_ifc_boundary_surface_attribute{}.uro_ifc_project_uro_long_name xml_buffer, uro_ifc_boundary_surface_attribute{}.uro_ifc_project_uro_phase xml_buffer, uro_ifc_boundary_surface_attribute{}.uro_ifc_project_uro_representation_contexts_uro_ifc_geometric_representation_context_uro_context_identifier xml_buffer, uro_ifc_boundary_surface_attribute{}.uro_ifc_project_uro_representation_contexts_uro_ifc_geometric_representation_context_uro_context_type xml_buffer, uro_ifc_boundary_surface_attribute{}.uro_ifc_project_uro_representation_contexts_uro_ifc_geometric_representation_context_uro_coordinate_space_dimension xml_int64, uro_ifc_boundary_surface_attribute{}.uro_ifc_project_uro_representation_contexts_uro_ifc_geometric_representation_context_uro_precision xml_real64, uro_ifc_boundary_surface_attribute{}.uro_ifc_project_uro_representation_contexts_uro_ifc_geometric_representation_context_uro_true_north xml_real64, uro_ifc_boundary_surface_attribute{}.uro_ifc_project_uro_units_in_context{}.uro_ifc_unit_uro_dimensions xml_int64, uro_ifc_boundary_surface_attribute{}.uro_ifc_project_uro_units_in_context{}.uro_ifc_unit_uro_unit_type xml_char(28), uro_ifc_boundary_surface_attribute{}.uro_ifc_project_uro_units_in_context{}.uro_ifc_unit_uro_perfix xml_buffer, uro_ifc_boundary_surface_attribute{}.uro_ifc_project_uro_units_in_context{}.uro_ifc_unit_uro_name xml_buffer, uro_ifc_boundary_surface_attribute{}.uro_ifc_projected_crs_uro_name xml_buffer, uro_ifc_boundary_surface_attribute{}.uro_ifc_projected_crs_uro_description xml_buffer, uro_ifc_boundary_surface_attribute{}.uro_ifc_projected_crs_uro_geodetic_datum xml_buffer, uro_ifc_boundary_surface_attribute{}.uro_ifc_projected_crs_uro_vertical_datum xml_buffer, uro_ifc_boundary_surface_attribute{}.uro_ifc_projected_crs_uro_map_unit xml_buffer, uro_ifc_boundary_surface_attribute{}.uro_ifc_projected_crs_uro_map_projection xml_buffer, uro_ifc_boundary_surface_attribute{}.uro_ifc_projected_crs_uro_map_zone xml_buffer, uro_ifc_boundary_surface_attribute{}.uro_ifc_pset_building_common_uro_building_id xml_real64,
      uro_ifc_boundary_surface_attribute{}.uro_ifc_pset_building_common_uro_building_id_units xml_buffer, uro_ifc_boundary_surface_attribute{}.uro_ifc_pset_building_common_uro_is_permanent_id xml_real64, uro_ifc_boundary_surface_attribute{}.uro_ifc_pset_building_common_uro_is_permanent_id_units xml_buffer, uro_ifc_boundary_surface_attribute{}.uro_ifc_pset_building_common_uro_main_fire_use xml_buffer, uro_ifc_boundary_surface_attribute{}.uro_ifc_pset_building_common_uro_ancillary_fire_use xml_buffer, uro_ifc_boundary_surface_attribute{}.uro_ifc_pset_building_common_uro_sprinkler_protection xml_boolean, uro_ifc_boundary_surface_attribute{}.uro_ifc_pset_building_common_uro_sprinkler_protection_automatic xml_boolean, uro_ifc_boundary_surface_attribute{}.uro_ifc_pset_building_common_uro_occupancy_type xml_buffer, uro_ifc_boundary_surface_attribute{}.uro_ifc_pset_building_common_uro_occupancy_type_codeSpace xml_buffer, uro_ifc_boundary_surface_attribute{}.uro_ifc_pset_building_common_uro_gross_planned_area xml_real64, uro_ifc_boundary_surface_attribute{}.uro_ifc_pset_building_common_uro_gross_planned_area_units xml_buffer, uro_ifc_boundary_surface_attribute{}.uro_ifc_pset_building_common_uro_number_of_storeys xml_int64, uro_ifc_boundary_surface_attribute{}.uro_ifc_pset_building_common_uro_year_of_construction xml_buffer, uro_ifc_boundary_surface_attribute{}.uro_ifc_pset_building_common_uro_is_landmarked xml_boolean, uro_ifc_boundary_surface_attribute{}.uro_ifc_pset_door_common_uro_reference xml_buffer, uro_ifc_boundary_surface_attribute{}.uro_ifc_pset_door_common_uro_acoustic_rating xml_buffer, uro_ifc_boundary_surface_attribute{}.uro_ifc_pset_door_common_uro_firerating xml_buffer, uro_ifc_boundary_surface_attribute{}.uro_ifc_pset_door_common_uro_security_rating xml_buffer, uro_ifc_boundary_surface_attribute{}.uro_ifc_pset_door_common_uro_is_external xml_boolean, uro_ifc_boundary_surface_attribute{}.uro_ifc_pset_door_common_uro_infiltration xml_real64, uro_ifc_boundary_surface_attribute{}.uro_ifc_pset_door_common_uro_thermal_transmittance xml_real64, uro_ifc_boundary_surface_attribute{}.uro_ifc_pset_door_common_uro_glazing_area_fraction xml_real64, uro_ifc_boundary_surface_attribute{}.uro_ifc_pset_door_common_uro_handicap_accessible xml_real64, uro_ifc_boundary_surface_attribute{}.uro_ifc_pset_door_common_uro_fire_exit xml_boolean, uro_ifc_boundary_surface_attribute{}.uro_ifc_pset_door_common_uro_self_closing xml_real64, uro_ifc_boundary_surface_attribute{}.uro_ifc_pset_door_common_uro_smoke_stop xml_boolean, uro_ifc_boundary_surface_attribute{}.uro_ifc_pset_opening_element_common_uro_reference xml_buffer, uro_ifc_boundary_surface_attribute{}.uro_ifc_pset_opening_element_common_uro_purpose xml_buffer, uro_ifc_boundary_surface_attribute{}.uro_ifc_pset_opening_element_common_uro_fire_exit xml_boolean, uro_ifc_boundary_surface_attribute{}.uro_ifc_pset_opening_element_common_uro_protected_opening xml_boolean,
      uro_ifc_boundary_surface_attribute{}.uro_ifc_pset_opening_element_common_uro_parallel_jambs xml_boolean, uro_ifc_boundary_surface_attribute{}.uro_ifc_pset_site_common_uro_buildable_area xml_real64, uro_ifc_boundary_surface_attribute{}.uro_ifc_pset_site_common_uro_buildable_area_units xml_buffer, uro_ifc_boundary_surface_attribute{}.uro_ifc_pset_site_common_uro_total_area xml_real64, uro_ifc_boundary_surface_attribute{}.uro_ifc_pset_site_common_uro_total_area_units xml_buffer, uro_ifc_boundary_surface_attribute{}.uro_ifc_pset_site_common_uro_building_height_limit xml_real64, uro_ifc_boundary_surface_attribute{}.uro_ifc_pset_site_common_uro_building_height_limit_units xml_buffer, uro_ifc_boundary_surface_attribute{}.uro_ifc_pset_space_common_uro_reference xml_buffer, uro_ifc_boundary_surface_attribute{}.uro_ifc_pset_space_common_uro_category xml_buffer, uro_ifc_boundary_surface_attribute{}.uro_ifc_pset_space_common_uro_category_codeSpace xml_buffer, uro_ifc_boundary_surface_attribute{}.uro_ifc_pset_space_common_uro_floor_covering xml_buffer, uro_ifc_boundary_surface_attribute{}.uro_ifc_pset_space_common_uro_wall_covering xml_buffer, uro_ifc_boundary_surface_attribute{}.uro_ifc_pset_space_common_uro_ceiling_covering xml_buffer, uro_ifc_boundary_surface_attribute{}.uro_ifc_pset_space_common_uro_skirting_covering xml_buffer, uro_ifc_boundary_surface_attribute{}.uro_ifc_pset_space_common_uro_gross_planned_area xml_real64, uro_ifc_boundary_surface_attribute{}.uro_ifc_pset_space_common_uro_gross_planned_area_units xml_buffer, uro_ifc_boundary_surface_attribute{}.uro_ifc_pset_space_common_uro_net_planned_area xml_real64, uro_ifc_boundary_surface_attribute{}.uro_ifc_pset_space_common_uro_net_planned_area_units xml_buffer, uro_ifc_boundary_surface_attribute{}.uro_ifc_pset_space_common_uro_publicly_accessible xml_boolean, uro_ifc_boundary_surface_attribute{}.uro_ifc_pset_space_common_uro_handicap_accessible xml_boolean, uro_ifc_boundary_surface_attribute{}.uro_ifc_pset_space_common_uro_concealed_flooring xml_boolean, uro_ifc_boundary_surface_attribute{}.uro_ifc_pset_space_common_uro_concealed_ceiling xml_boolean, uro_ifc_boundary_surface_attribute{}.uro_ifc_pset_window_common_uro_reference xml_buffer, uro_ifc_boundary_surface_attribute{}.uro_ifc_pset_window_common_uro_acoustic_rating xml_buffer, uro_ifc_boundary_surface_attribute{}.uro_ifc_pset_window_common_uro_firerating xml_buffer, uro_ifc_boundary_surface_attribute{}.uro_ifc_pset_window_common_uro_security_rating xml_buffer, uro_ifc_boundary_surface_attribute{}.uro_ifc_pset_window_common_uro_is_external xml_boolean, uro_ifc_boundary_surface_attribute{}.uro_ifc_pset_window_common_uro_infiltration xml_real64, uro_ifc_boundary_surface_attribute{}.uro_ifc_pset_window_common_uro_thermal_transmittance xml_real64, uro_ifc_boundary_surface_attribute{}.uro_ifc_pset_window_common_uro_glazing_area_fraction xml_real64,
      uro_ifc_boundary_surface_attribute{}.uro_ifc_pset_window_common_uro_smoke_stop xml_boolean, uro_ifc_boundary_surface_attribute{}.uro_ifc_site_uro_global_id xml_buffer, uro_ifc_boundary_surface_attribute{}.uro_ifc_site_uro_name xml_buffer, uro_ifc_boundary_surface_attribute{}.uro_ifc_site_uro_description xml_buffer, uro_ifc_boundary_surface_attribute{}.uro_ifc_site_uro_object_type xml_buffer, uro_ifc_boundary_surface_attribute{}.uro_ifc_site_uro_long_name xml_buffer, uro_ifc_boundary_surface_attribute{}.uro_ifc_site_uro_composition_type xml_char(7), uro_ifc_boundary_surface_attribute{}.uro_ifc_site_uro_ref_longitude xml_real64, uro_ifc_boundary_surface_attribute{}.uro_ifc_site_uro_ref_latitude xml_real64, uro_ifc_boundary_surface_attribute{}.uro_ifc_site_uro_ref_elevation xml_real64, uro_ifc_boundary_surface_attribute{}.uro_ifc_site_uro_ref_elevation_units xml_buffer, uro_ifc_boundary_surface_attribute{}.uro_ifc_site_uro_land_title_number xml_buffer, uro_ifc_boundary_surface_attribute{}.uro_ifc_site_uro_site_address_xlink_href xml_buffer, uro_ifc_boundary_surface_attribute{}.uro_ifc_space_uro_global_id xml_buffer, uro_ifc_boundary_surface_attribute{}.uro_ifc_space_uro_name xml_buffer, uro_ifc_boundary_surface_attribute{}.uro_ifc_space_uro_description xml_buffer, uro_ifc_boundary_surface_attribute{}.uro_ifc_space_uro_object_type xml_buffer, uro_ifc_boundary_surface_attribute{}.uro_ifc_space_uro_long_name xml_buffer, uro_ifc_boundary_surface_attribute{}.uro_ifc_space_uro_composition_type xml_char(7), uro_ifc_boundary_surface_attribute{}.uro_ifc_space_uro_interioror_exterior_space xml_char(10), uro_ifc_boundary_surface_attribute{}.uro_ifc_space_uro_elevation_with_flooring xml_real64, uro_ifc_boundary_surface_attribute{}.uro_ifc_space_uro_elevation_with_flooring_units xml_buffer, uro_ifc_boundary_surface_attribute{}.uro_ifc_space_base_quantity_uro_nominal_height xml_real64, uro_ifc_boundary_surface_attribute{}.uro_ifc_space_base_quantity_uro_nominal_height_units xml_buffer, uro_ifc_boundary_surface_attribute{}.uro_ifc_space_base_quantity_uro_clear_height xml_real64, uro_ifc_boundary_surface_attribute{}.uro_ifc_space_base_quantity_uro_clear_height_units xml_buffer, uro_ifc_boundary_surface_attribute{}.uro_ifc_space_base_quantity_uro_finish_ceiling_height xml_real64, uro_ifc_boundary_surface_attribute{}.uro_ifc_space_base_quantity_uro_finish_ceiling_height_units xml_buffer, uro_ifc_boundary_surface_attribute{}.uro_ifc_space_base_quantity_uro_gross_perimeter xml_real64, uro_ifc_boundary_surface_attribute{}.uro_ifc_space_base_quantity_uro_gross_perimeter_units xml_buffer,
      uro_ifc_boundary_surface_attribute{}.uro_ifc_space_base_quantity_uro_net_perimeter xml_real64, uro_ifc_boundary_surface_attribute{}.uro_ifc_space_base_quantity_uro_net_perimeter_units xml_buffer, uro_ifc_boundary_surface_attribute{}.uro_ifc_space_base_quantity_uro_gross_ceiling_area xml_real64, uro_ifc_boundary_surface_attribute{}.uro_ifc_space_base_quantity_uro_gross_ceiling_area_units xml_buffer, uro_ifc_boundary_surface_attribute{}.uro_ifc_space_base_quantity_uro_gross_floor_area xml_real64, uro_ifc_boundary_surface_attribute{}.uro_ifc_space_base_quantity_uro_gross_floor_area_units xml_buffer, uro_ifc_boundary_surface_attribute{}.uro_ifc_space_base_quantity_uro_net_ceiling_area xml_real64, uro_ifc_boundary_surface_attribute{}.uro_ifc_space_base_quantity_uro_net_ceiling_area_units xml_buffer, uro_ifc_boundary_surface_attribute{}.uro_ifc_space_base_quantity_uro_net_floor_area xml_real64, uro_ifc_boundary_surface_attribute{}.uro_ifc_space_base_quantity_uro_net_floor_area_units xml_buffer, uro_ifc_boundary_surface_attribute{}.uro_ifc_space_base_quantity_uro_gross_wall_area xml_real64, uro_ifc_boundary_surface_attribute{}.uro_ifc_space_base_quantity_uro_gross_wall_area_units xml_buffer, uro_ifc_boundary_surface_attribute{}.uro_ifc_space_base_quantity_uro_net_wall_area xml_real64, uro_ifc_boundary_surface_attribute{}.uro_ifc_space_base_quantity_uro_net_wall_area_units xml_buffer, uro_ifc_boundary_surface_attribute{}.uro_ifc_space_base_quantity_uro_gross_volume xml_real64, uro_ifc_boundary_surface_attribute{}.uro_ifc_space_base_quantity_uro_gross_volume_units xml_buffer, uro_ifc_boundary_surface_attribute{}.uro_ifc_space_base_quantity_uro_net_volume xml_real64, uro_ifc_boundary_surface_attribute{}.uro_ifc_space_base_quantity_uro_net_volume_units xml_buffer, uro_ifc_boundary_surface_attribute{}.uro_ifc_wall_uro_global_id xml_buffer, uro_ifc_boundary_surface_attribute{}.uro_ifc_wall_uro_name xml_buffer, uro_ifc_boundary_surface_attribute{}.uro_ifc_wall_uro_description xml_buffer, uro_ifc_boundary_surface_attribute{}.uro_ifc_wall_uro_object_type xml_buffer, uro_ifc_boundary_surface_attribute{}.uro_ifc_wall_uro_tag xml_buffer, uro_ifc_boundary_surface_attribute{}.uro_ifc_wall_uro_element_type xml_buffer, uro_ifc_boundary_surface_attribute{}.uro_ifc_wall_uro_element_type_codeSpace xml_buffer, uro_ifc_boundary_surface_attribute{}.uro_ifc_wall_uro_predefined_type xml_buffer, uro_ifc_boundary_surface_attribute{}.uro_ifc_wall_uro_predefined_type_codeSpace xml_buffer, uro_ifc_boundary_surface_attribute{}.uro_ifc_wall_uro_shape_type xml_buffer, uro_ifc_boundary_surface_attribute{}.uro_ifc_wall_uro_shape_type_codeSpace xml_buffer, uro_ifc_boundary_surface_attribute{}.uro_ifc_wall_uro_number_of_riser xml_int64,
      uro_ifc_boundary_surface_attribute{}.uro_ifc_wall_uro_number_of_treads xml_int64, uro_ifc_boundary_surface_attribute{}.uro_ifc_wall_uro_riser_height xml_int64, uro_ifc_boundary_surface_attribute{}.uro_ifc_wall_uro_tread_length xml_int64, uro_ifc_boundary_surface_attribute{}.uro_ifc_wall_uro_operation_type xml_char(11), uro_ifc_boundary_surface_attribute{}.uro_ifc_wall_uro_capacity_by_weight xml_real64, uro_ifc_boundary_surface_attribute{}.uro_ifc_wall_uro_capacity_by_weight_units xml_buffer, uro_ifc_boundary_surface_attribute{}.uro_ifc_wall_uro_capacity_by_number xml_int64, uro_ifc_boundary_surface_attribute{}.uro_ifc_wall_uro_nominal_length xml_real64, uro_ifc_boundary_surface_attribute{}.uro_ifc_wall_uro_nominal_length_units xml_buffer, uro_ifc_boundary_surface_attribute{}.uro_ifc_wall_uro_nominal_width xml_real64, uro_ifc_boundary_surface_attribute{}.uro_ifc_wall_uro_nominal_width_units xml_buffer, uro_ifc_boundary_surface_attribute{}.uro_ifc_wall_uro_nominal_height xml_real64, uro_ifc_boundary_surface_attribute{}.uro_ifc_wall_uro_nominal_height_units xml_buffer, uro_ifc_boundary_surface_attribute{}.uro_ifc_wall_uro_gross_foot_print_area xml_real64, uro_ifc_boundary_surface_attribute{}.uro_ifc_wall_uro_gross_foot_print_area_units xml_buffer, uro_ifc_boundary_surface_attribute{}.uro_ifc_wall_uro_net_foot_print_area xml_real64, uro_ifc_boundary_surface_attribute{}.uro_ifc_wall_uro_net_foot_print_area_units xml_buffer, uro_ifc_boundary_surface_attribute{}.uro_ifc_wall_uro_gross_side_area xml_real64, uro_ifc_boundary_surface_attribute{}.uro_ifc_wall_uro_gross_side_area_units xml_buffer, uro_ifc_boundary_surface_attribute{}.uro_ifc_wall_uro_net_side_area xml_real64, uro_ifc_boundary_surface_attribute{}.uro_ifc_wall_uro_net_side_area_units xml_buffer, uro_ifc_boundary_surface_attribute{}.uro_ifc_wall_uro_gross_side_area_left xml_real64, uro_ifc_boundary_surface_attribute{}.uro_ifc_wall_uro_gross_side_area_left_units xml_buffer, uro_ifc_boundary_surface_attribute{}.uro_ifc_wall_uro_net_side_area_left xml_real64, uro_ifc_boundary_surface_attribute{}.uro_ifc_wall_uro_net_side_area_left_units xml_buffer, uro_ifc_boundary_surface_attribute{}.uro_ifc_wall_uro_gross_side_area_right xml_real64, uro_ifc_boundary_surface_attribute{}.uro_ifc_wall_uro_gross_side_area_right_units xml_buffer, uro_ifc_boundary_surface_attribute{}.uro_ifc_wall_uro_net_side_area_right xml_real64, uro_ifc_boundary_surface_attribute{}.uro_ifc_wall_uro_net_side_area_right_units xml_buffer, uro_ifc_boundary_surface_attribute{}.uro_ifc_wall_uro_gross_volume xml_real64,
      uro_ifc_boundary_surface_attribute{}.uro_ifc_wall_uro_gross_volume_units xml_buffer, uro_ifc_boundary_surface_attribute{}.uro_ifc_wall_uro_net_volume xml_real64, uro_ifc_boundary_surface_attribute{}.uro_ifc_wall_uro_net_volume_units xml_buffer, uro_ifc_boundary_surface_attribute{}.uro_ifc_wall_standard_case_uro_global_id xml_buffer, uro_ifc_boundary_surface_attribute{}.uro_ifc_wall_standard_case_uro_name xml_buffer, uro_ifc_boundary_surface_attribute{}.uro_ifc_wall_standard_case_uro_description xml_buffer, uro_ifc_boundary_surface_attribute{}.uro_ifc_wall_standard_case_uro_object_type xml_buffer, uro_ifc_boundary_surface_attribute{}.uro_ifc_wall_standard_case_uro_tag xml_buffer, uro_ifc_boundary_surface_attribute{}.uro_ifc_wall_standard_case_uro_element_type xml_buffer, uro_ifc_boundary_surface_attribute{}.uro_ifc_wall_standard_case_uro_element_type_codeSpace xml_buffer, uro_ifc_boundary_surface_attribute{}.uro_ifc_wall_standard_case_uro_predefined_type xml_buffer, uro_ifc_boundary_surface_attribute{}.uro_ifc_wall_standard_case_uro_predefined_type_codeSpace xml_buffer, uro_ifc_boundary_surface_attribute{}.uro_ifc_wall_standard_case_uro_shape_type xml_buffer, uro_ifc_boundary_surface_attribute{}.uro_ifc_wall_standard_case_uro_shape_type_codeSpace xml_buffer, uro_ifc_boundary_surface_attribute{}.uro_ifc_wall_standard_case_uro_number_of_riser xml_int64, uro_ifc_boundary_surface_attribute{}.uro_ifc_wall_standard_case_uro_number_of_treads xml_int64, uro_ifc_boundary_surface_attribute{}.uro_ifc_wall_standard_case_uro_riser_height xml_int64, uro_ifc_boundary_surface_attribute{}.uro_ifc_wall_standard_case_uro_tread_length xml_int64, uro_ifc_boundary_surface_attribute{}.uro_ifc_wall_standard_case_uro_operation_type xml_char(11), uro_ifc_boundary_surface_attribute{}.uro_ifc_wall_standard_case_uro_capacity_by_weight xml_real64, uro_ifc_boundary_surface_attribute{}.uro_ifc_wall_standard_case_uro_capacity_by_weight_units xml_buffer, uro_ifc_boundary_surface_attribute{}.uro_ifc_wall_standard_case_uro_capacity_by_number xml_int64, uro_ifc_boundary_surface_attribute{}.uro_ifc_wall_standard_case_uro_nominal_length xml_real64, uro_ifc_boundary_surface_attribute{}.uro_ifc_wall_standard_case_uro_nominal_length_units xml_buffer, uro_ifc_boundary_surface_attribute{}.uro_ifc_wall_standard_case_uro_nominal_width xml_real64, uro_ifc_boundary_surface_attribute{}.uro_ifc_wall_standard_case_uro_nominal_width_units xml_buffer, uro_ifc_boundary_surface_attribute{}.uro_ifc_wall_standard_case_uro_nominal_height xml_real64, uro_ifc_boundary_surface_attribute{}.uro_ifc_wall_standard_case_uro_nominal_height_units xml_buffer, uro_ifc_boundary_surface_attribute{}.uro_ifc_wall_standard_case_uro_gross_foot_print_area xml_real64, uro_ifc_boundary_surface_attribute{}.uro_ifc_wall_standard_case_uro_gross_foot_print_area_units xml_buffer,
      uro_ifc_boundary_surface_attribute{}.uro_ifc_wall_standard_case_uro_net_foot_print_area xml_real64, uro_ifc_boundary_surface_attribute{}.uro_ifc_wall_standard_case_uro_net_foot_print_area_units xml_buffer, uro_ifc_boundary_surface_attribute{}.uro_ifc_wall_standard_case_uro_gross_side_area xml_real64, uro_ifc_boundary_surface_attribute{}.uro_ifc_wall_standard_case_uro_gross_side_area_units xml_buffer, uro_ifc_boundary_surface_attribute{}.uro_ifc_wall_standard_case_uro_net_side_area xml_real64, uro_ifc_boundary_surface_attribute{}.uro_ifc_wall_standard_case_uro_net_side_area_units xml_buffer, uro_ifc_boundary_surface_attribute{}.uro_ifc_wall_standard_case_uro_gross_side_area_left xml_real64, uro_ifc_boundary_surface_attribute{}.uro_ifc_wall_standard_case_uro_gross_side_area_left_units xml_buffer, uro_ifc_boundary_surface_attribute{}.uro_ifc_wall_standard_case_uro_net_side_area_left xml_real64, uro_ifc_boundary_surface_attribute{}.uro_ifc_wall_standard_case_uro_net_side_area_left_units xml_buffer, uro_ifc_boundary_surface_attribute{}.uro_ifc_wall_standard_case_uro_gross_side_area_right xml_real64, uro_ifc_boundary_surface_attribute{}.uro_ifc_wall_standard_case_uro_gross_side_area_right_units xml_buffer, uro_ifc_boundary_surface_attribute{}.uro_ifc_wall_standard_case_uro_net_side_area_right xml_real64, uro_ifc_boundary_surface_attribute{}.uro_ifc_wall_standard_case_uro_net_side_area_right_units xml_buffer, uro_ifc_boundary_surface_attribute{}.uro_ifc_wall_standard_case_uro_gross_volume xml_real64, uro_ifc_boundary_surface_attribute{}.uro_ifc_wall_standard_case_uro_gross_volume_units xml_buffer, uro_ifc_boundary_surface_attribute{}.uro_ifc_wall_standard_case_uro_net_volume xml_real64, uro_ifc_boundary_surface_attribute{}.uro_ifc_wall_standard_case_uro_net_volume_units xml_buffer, uro_ifc_boundary_surface_attribute{}.uro_ifc_window_uro_global_id xml_buffer, uro_ifc_boundary_surface_attribute{}.uro_ifc_window_uro_name xml_buffer, uro_ifc_boundary_surface_attribute{}.uro_ifc_window_uro_description xml_buffer, uro_ifc_boundary_surface_attribute{}.uro_ifc_window_uro_object_type xml_buffer, uro_ifc_boundary_surface_attribute{}.uro_ifc_window_uro_tag xml_buffer, uro_ifc_boundary_surface_attribute{}.uro_ifc_window_uro_element_type xml_buffer, uro_ifc_boundary_surface_attribute{}.uro_ifc_window_uro_element_type_codeSpace xml_buffer, uro_ifc_boundary_surface_attribute{}.uro_ifc_window_uro_predefined_type xml_buffer, uro_ifc_boundary_surface_attribute{}.uro_ifc_window_uro_predefined_type_codeSpace xml_buffer, uro_ifc_boundary_surface_attribute{}.uro_ifc_window_uro_shape_type xml_buffer, uro_ifc_boundary_surface_attribute{}.uro_ifc_window_uro_shape_type_codeSpace xml_buffer, uro_ifc_boundary_surface_attribute{}.uro_ifc_window_uro_number_of_riser xml_int64,
      uro_ifc_boundary_surface_attribute{}.uro_ifc_window_uro_number_of_treads xml_int64, uro_ifc_boundary_surface_attribute{}.uro_ifc_window_uro_riser_height xml_int64, uro_ifc_boundary_surface_attribute{}.uro_ifc_window_uro_tread_length xml_int64, uro_ifc_boundary_surface_attribute{}.uro_ifc_window_uro_operation_type xml_char(11), uro_ifc_boundary_surface_attribute{}.uro_ifc_window_uro_capacity_by_weight xml_real64, uro_ifc_boundary_surface_attribute{}.uro_ifc_window_uro_capacity_by_weight_units xml_buffer, uro_ifc_boundary_surface_attribute{}.uro_ifc_window_uro_capacity_by_number xml_int64, uro_ifc_boundary_surface_attribute{}.uro_ifc_window_uro_overall_height xml_real64, uro_ifc_boundary_surface_attribute{}.uro_ifc_window_uro_overall_height_units xml_buffer, uro_ifc_boundary_surface_attribute{}.uro_ifc_window_uro_overall_width xml_real64, uro_ifc_boundary_surface_attribute{}.uro_ifc_window_uro_overall_width_units xml_buffer
Note: AttributeManager_13 : Input / Room ソリッドに集約
Junction_8
    -> Junction_56
Note: ClosureSurface / AttributeManager_3 : Output
Junction_56
    -> AttributeManager_13
Junction_80
    -> Junction_78
Junction_78
    -> Triangulator_2
TestFilter
    DEFAULT_VALUE = InteriorWallSurface
    PASSED_TEST_GROUP_OUTPUT = FIRST
    TEST_LIST = "BOOL_OP,OR,COMPOSITE_TEST,""""""1"""""",TEST_CLAUSE,TEST @Value(_surfaceNormalZ) < -0.5",CeilingSurface,"BOOL_OP,OR,COMPOSITE_TEST,""""""1"""""",TEST_CLAUSE,TEST 0.5 < @Value(_surfaceNormalZ)",FloorSurface
    CeilingSurface -> AttributeManager_5
    FloorSurface -> AttributeManager_6
    InteriorWallSurface -> AttributeManager_7
Note: 天井: CeilingSurface
AttributeManager_5
    ATTR_TABLE:
      SET_TO gml_id = ceil_@UUID()
      SET_TO _citygml_feature_type = CeilingSurface
      REMOVE _surfaceNormalX
      REMOVE _surfaceNormalY
      REMOVE _surfaceNormalZ
      REMOVE _pointOnSurfaceX
      REMOVE _pointOnSurfaceY
      REMOVE _pointOnSurfaceZ
      SET_TO citygml_lod_name = lod4MultiSurface
      SET_TO citygml_feature_role = boundedBy
    -> GeometryPropertySetter_4
    -> Junction_17
GeometryPropertySetter_4
    GQUERY:
      for $geom in //geometry
      where $geom/count(parent::geometry) = 0
      return number($geom/@fme_id)
    OVERWRITE_CHOICE = Yes
    REMOVE_ATTRIBUTE = Yes
    SETTYPE_PARAM = Traits From Attributes
    SRC_ATTRS = citygml_lod_name gml_id
    SET -> AttributeCreator_6
AttributeCreator_6
    ATTR_TABLE:
      SET_TO gml_id = @Value(_boundary_gml_id)
      SET_TO gml_parent_id = @Value(_room_gml_id)
    -> PLATEAU.IfcReprojector_4 [IfcFeature]
PLATEAU.IfcReprojector_4
    DEST_COORDSYS = $(DEST_COORDSYS)
    LENGTH_MULTIPLIER = @Value(_lengthmultiplier)
    REPROJECTION_PARAMS = @Value(_reprojection_params)
    Reprojected -> CeilingSurface (writer CITYGML_2)
CeilingSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, uro_ifc_boundary_surface_attribute{}.uro_ifc_building_uro_global_id xml_buffer, uro_ifc_boundary_surface_attribute{}.uro_ifc_building_uro_name xml_buffer, uro_ifc_boundary_surface_attribute{}.uro_ifc_building_uro_description xml_buffer, uro_ifc_boundary_surface_attribute{}.uro_ifc_building_uro_object_type xml_buffer, uro_ifc_boundary_surface_attribute{}.uro_ifc_building_uro_long_name xml_buffer, uro_ifc_boundary_surface_attribute{}.uro_ifc_building_uro_composition_type xml_char(7), uro_ifc_boundary_surface_attribute{}.uro_ifc_building_uro_elevation_of_ref_height xml_real64, uro_ifc_boundary_surface_attribute{}.uro_ifc_building_uro_elevation_of_ref_height_units xml_buffer, uro_ifc_boundary_surface_attribute{}.uro_ifc_building_uro_elevation_of_terrain xml_real64, uro_ifc_boundary_surface_attribute{}.uro_ifc_building_uro_elevation_of_terrain_units xml_buffer, uro_ifc_boundary_surface_attribute{}.uro_ifc_building_uro_building_address_xlink_href xml_buffer, uro_ifc_boundary_surface_attribute{}.uro_ifc_building_element_uro_global_id xml_buffer, uro_ifc_boundary_surface_attribute{}.uro_ifc_building_element_uro_name xml_buffer, uro_ifc_boundary_surface_attribute{}.uro_ifc_building_element_uro_description xml_buffer,
      uro_ifc_boundary_surface_attribute{}.uro_ifc_building_element_uro_object_type xml_buffer, uro_ifc_boundary_surface_attribute{}.uro_ifc_building_element_uro_tag xml_buffer, uro_ifc_boundary_surface_attribute{}.uro_ifc_building_element_uro_element_type xml_buffer, uro_ifc_boundary_surface_attribute{}.uro_ifc_building_element_uro_element_type_codeSpace xml_buffer, uro_ifc_boundary_surface_attribute{}.uro_ifc_building_element_uro_predefined_type xml_buffer, uro_ifc_boundary_surface_attribute{}.uro_ifc_building_element_uro_predefined_type_codeSpace xml_buffer, uro_ifc_boundary_surface_attribute{}.uro_ifc_building_element_uro_shape_type xml_buffer, uro_ifc_boundary_surface_attribute{}.uro_ifc_building_element_uro_shape_type_codeSpace xml_buffer, uro_ifc_boundary_surface_attribute{}.uro_ifc_building_element_uro_number_of_riser xml_int64, uro_ifc_boundary_surface_attribute{}.uro_ifc_building_element_uro_number_of_treads xml_int64, uro_ifc_boundary_surface_attribute{}.uro_ifc_building_element_uro_riser_height xml_int64, uro_ifc_boundary_surface_attribute{}.uro_ifc_building_element_uro_tread_length xml_int64, uro_ifc_boundary_surface_attribute{}.uro_ifc_building_element_uro_operation_type xml_char(11), uro_ifc_boundary_surface_attribute{}.uro_ifc_building_element_uro_capacity_by_weight xml_real64, uro_ifc_boundary_surface_attribute{}.uro_ifc_building_element_uro_capacity_by_weight_units xml_buffer, uro_ifc_boundary_surface_attribute{}.uro_ifc_building_element_uro_capacity_by_number xml_int64, uro_ifc_boundary_surface_attribute{}.uro_ifc_building_storey_uro_global_id xml_buffer, uro_ifc_boundary_surface_attribute{}.uro_ifc_building_storey_uro_name xml_buffer, uro_ifc_boundary_surface_attribute{}.uro_ifc_building_storey_uro_description xml_buffer, uro_ifc_boundary_surface_attribute{}.uro_ifc_building_storey_uro_object_type xml_buffer, uro_ifc_boundary_surface_attribute{}.uro_ifc_building_storey_uro_long_name xml_buffer, uro_ifc_boundary_surface_attribute{}.uro_ifc_building_storey_uro_composition_type xml_char(7), uro_ifc_boundary_surface_attribute{}.uro_ifc_building_storey_uro_elevation xml_real64, uro_ifc_boundary_surface_attribute{}.uro_ifc_building_storey_uro_elevation_units xml_buffer, uro_ifc_boundary_surface_attribute{}.uro_ifc_classification_reference_uro_location xml_buffer, uro_ifc_boundary_surface_attribute{}.uro_ifc_classification_reference_uro_item_reference xml_buffer, uro_ifc_boundary_surface_attribute{}.uro_ifc_classification_reference_uro_item_reference_codeSpace xml_buffer, uro_ifc_boundary_surface_attribute{}.uro_ifc_classification_reference_uro_name xml_buffer, uro_ifc_boundary_surface_attribute{}.uro_ifc_classification_reference_uro_name_codeSpace xml_buffer, uro_ifc_boundary_surface_attribute{}.uro_ifc_classification_reference_uro_reference_source_uro_ifc_classification_uro_source xml_buffer,
      uro_ifc_boundary_surface_attribute{}.uro_ifc_classification_reference_uro_reference_source_uro_ifc_classification_uro_edition xml_buffer, uro_ifc_boundary_surface_attribute{}.uro_ifc_classification_reference_uro_reference_source_uro_ifc_classification_uro_edition_date xml_date, uro_ifc_boundary_surface_attribute{}.uro_ifc_classification_reference_uro_reference_source_uro_ifc_classification_uro_name xml_buffer, uro_ifc_boundary_surface_attribute{}.uro_ifc_coordinate_reference_system_uro_name xml_buffer, uro_ifc_boundary_surface_attribute{}.uro_ifc_coordinate_reference_system_uro_description xml_buffer, uro_ifc_boundary_surface_attribute{}.uro_ifc_coordinate_reference_system_uro_geodetic_datum xml_buffer, uro_ifc_boundary_surface_attribute{}.uro_ifc_coordinate_reference_system_uro_vertical_datum xml_buffer, uro_ifc_boundary_surface_attribute{}.uro_ifc_curtain_wall_uro_global_id xml_buffer, uro_ifc_boundary_surface_attribute{}.uro_ifc_curtain_wall_uro_name xml_buffer, uro_ifc_boundary_surface_attribute{}.uro_ifc_curtain_wall_uro_description xml_buffer, uro_ifc_boundary_surface_attribute{}.uro_ifc_curtain_wall_uro_object_type xml_buffer, uro_ifc_boundary_surface_attribute{}.uro_ifc_curtain_wall_uro_tag xml_buffer, uro_ifc_boundary_surface_attribute{}.uro_ifc_curtain_wall_uro_element_type xml_buffer, uro_ifc_boundary_surface_attribute{}.uro_ifc_curtain_wall_uro_element_type_codeSpace xml_buffer, uro_ifc_boundary_surface_attribute{}.uro_ifc_curtain_wall_uro_predefined_type xml_buffer, uro_ifc_boundary_surface_attribute{}.uro_ifc_curtain_wall_uro_predefined_type_codeSpace xml_buffer, uro_ifc_boundary_surface_attribute{}.uro_ifc_curtain_wall_uro_shape_type xml_buffer, uro_ifc_boundary_surface_attribute{}.uro_ifc_curtain_wall_uro_shape_type_codeSpace xml_buffer, uro_ifc_boundary_surface_attribute{}.uro_ifc_curtain_wall_uro_number_of_riser xml_int64, uro_ifc_boundary_surface_attribute{}.uro_ifc_curtain_wall_uro_number_of_treads xml_int64, uro_ifc_boundary_surface_attribute{}.uro_ifc_curtain_wall_uro_riser_height xml_int64, uro_ifc_boundary_surface_attribute{}.uro_ifc_curtain_wall_uro_tread_length xml_int64, uro_ifc_boundary_surface_attribute{}.uro_ifc_curtain_wall_uro_operation_type xml_char(11), uro_ifc_boundary_surface_attribute{}.uro_ifc_curtain_wall_uro_capacity_by_weight xml_real64, uro_ifc_boundary_surface_attribute{}.uro_ifc_curtain_wall_uro_capacity_by_weight_units xml_buffer, uro_ifc_boundary_surface_attribute{}.uro_ifc_curtain_wall_uro_capacity_by_number xml_int64, uro_ifc_boundary_surface_attribute{}.uro_ifc_door_uro_global_id xml_buffer, uro_ifc_boundary_surface_attribute{}.uro_ifc_door_uro_name xml_buffer, uro_ifc_boundary_surface_attribute{}.uro_ifc_door_uro_description xml_buffer, uro_ifc_boundary_surface_attribute{}.uro_ifc_door_uro_object_type xml_buffer,
      uro_ifc_boundary_surface_attribute{}.uro_ifc_door_uro_tag xml_buffer, uro_ifc_boundary_surface_attribute{}.uro_ifc_door_uro_element_type xml_buffer, uro_ifc_boundary_surface_attribute{}.uro_ifc_door_uro_element_type_codeSpace xml_buffer, uro_ifc_boundary_surface_attribute{}.uro_ifc_door_uro_predefined_type xml_buffer, uro_ifc_boundary_surface_attribute{}.uro_ifc_door_uro_predefined_type_codeSpace xml_buffer, uro_ifc_boundary_surface_attribute{}.uro_ifc_door_uro_shape_type xml_buffer, uro_ifc_boundary_surface_attribute{}.uro_ifc_door_uro_shape_type_codeSpace xml_buffer, uro_ifc_boundary_surface_attribute{}.uro_ifc_door_uro_number_of_riser xml_int64, uro_ifc_boundary_surface_attribute{}.uro_ifc_door_uro_number_of_treads xml_int64, uro_ifc_boundary_surface_attribute{}.uro_ifc_door_uro_riser_height xml_int64, uro_ifc_boundary_surface_attribute{}.uro_ifc_door_uro_tread_length xml_int64, uro_ifc_boundary_surface_attribute{}.uro_ifc_door_uro_operation_type xml_char(11), uro_ifc_boundary_surface_attribute{}.uro_ifc_door_uro_capacity_by_weight xml_real64, uro_ifc_boundary_surface_attribute{}.uro_ifc_door_uro_capacity_by_weight_units xml_buffer, uro_ifc_boundary_surface_attribute{}.uro_ifc_door_uro_capacity_by_number xml_int64, uro_ifc_boundary_surface_attribute{}.uro_ifc_door_uro_overall_height xml_real64, uro_ifc_boundary_surface_attribute{}.uro_ifc_door_uro_overall_height_units xml_buffer, uro_ifc_boundary_surface_attribute{}.uro_ifc_door_uro_overall_width xml_real64, uro_ifc_boundary_surface_attribute{}.uro_ifc_door_uro_overall_width_units xml_buffer, uro_ifc_boundary_surface_attribute{}.uro_ifc_furnishing_element_uro_global_id xml_buffer, uro_ifc_boundary_surface_attribute{}.uro_ifc_furnishing_element_uro_name xml_buffer, uro_ifc_boundary_surface_attribute{}.uro_ifc_furnishing_element_uro_description xml_buffer, uro_ifc_boundary_surface_attribute{}.uro_ifc_furnishing_element_uro_object_type xml_buffer, uro_ifc_boundary_surface_attribute{}.uro_ifc_furnishing_element_uro_tag xml_buffer, uro_ifc_boundary_surface_attribute{}.uro_ifc_map_conversion_uro_source_crs_uro_crs_uro_ifc_projected_crs_uro_name xml_buffer, uro_ifc_boundary_surface_attribute{}.uro_ifc_map_conversion_uro_source_crs_uro_crs_uro_ifc_projected_crs_uro_description xml_buffer, uro_ifc_boundary_surface_attribute{}.uro_ifc_map_conversion_uro_source_crs_uro_crs_uro_ifc_projected_crs_uro_geodetic_datum xml_buffer, uro_ifc_boundary_surface_attribute{}.uro_ifc_map_conversion_uro_source_crs_uro_crs_uro_ifc_projected_crs_uro_vertical_datum xml_buffer, uro_ifc_boundary_surface_attribute{}.uro_ifc_map_conversion_uro_source_crs_uro_crs_uro_ifc_projected_crs_uro_map_unit xml_buffer, uro_ifc_boundary_surface_attribute{}.uro_ifc_map_conversion_uro_source_crs_uro_crs_uro_ifc_projected_crs_uro_map_projection xml_buffer,
      uro_ifc_boundary_surface_attribute{}.uro_ifc_map_conversion_uro_source_crs_uro_crs_uro_ifc_projected_crs_uro_map_zone xml_buffer, uro_ifc_boundary_surface_attribute{}.uro_ifc_map_conversion_uro_source_crs_uro_crs_uro_ifc_coordinate_reference_system_uro_name xml_buffer, uro_ifc_boundary_surface_attribute{}.uro_ifc_map_conversion_uro_source_crs_uro_crs_uro_ifc_coordinate_reference_system_uro_description xml_buffer, uro_ifc_boundary_surface_attribute{}.uro_ifc_map_conversion_uro_source_crs_uro_crs_uro_ifc_coordinate_reference_system_uro_geodetic_datum xml_buffer, uro_ifc_boundary_surface_attribute{}.uro_ifc_map_conversion_uro_source_crs_uro_crs_uro_ifc_coordinate_reference_system_uro_vertical_datum xml_buffer, uro_ifc_boundary_surface_attribute{}.uro_ifc_map_conversion_uro_source_crs_uro_context_uro_ifc_geometric_representation_context_uro_context_identifier xml_buffer, uro_ifc_boundary_surface_attribute{}.uro_ifc_map_conversion_uro_source_crs_uro_context_uro_ifc_geometric_representation_context_uro_context_type xml_buffer, uro_ifc_boundary_surface_attribute{}.uro_ifc_map_conversion_uro_source_crs_uro_context_uro_ifc_geometric_representation_context_uro_coordinate_space_dimension xml_int64, uro_ifc_boundary_surface_attribute{}.uro_ifc_map_conversion_uro_source_crs_uro_context_uro_ifc_geometric_representation_context_uro_precision xml_real64, uro_ifc_boundary_surface_attribute{}.uro_ifc_map_conversion_uro_source_crs_uro_context_uro_ifc_geometric_representation_context_uro_true_north xml_real64, uro_ifc_boundary_surface_attribute{}.uro_ifc_map_conversion_uro_target_crs_uro_ifc_projected_crs_uro_name xml_buffer, uro_ifc_boundary_surface_attribute{}.uro_ifc_map_conversion_uro_target_crs_uro_ifc_projected_crs_uro_description xml_buffer, uro_ifc_boundary_surface_attribute{}.uro_ifc_map_conversion_uro_target_crs_uro_ifc_projected_crs_uro_geodetic_datum xml_buffer, uro_ifc_boundary_surface_attribute{}.uro_ifc_map_conversion_uro_target_crs_uro_ifc_projected_crs_uro_vertical_datum xml_buffer, uro_ifc_boundary_surface_attribute{}.uro_ifc_map_conversion_uro_target_crs_uro_ifc_projected_crs_uro_map_unit xml_buffer, uro_ifc_boundary_surface_attribute{}.uro_ifc_map_conversion_uro_target_crs_uro_ifc_projected_crs_uro_map_projection xml_buffer, uro_ifc_boundary_surface_attribute{}.uro_ifc_map_conversion_uro_target_crs_uro_ifc_projected_crs_uro_map_zone xml_buffer, uro_ifc_boundary_surface_attribute{}.uro_ifc_map_conversion_uro_target_crs_uro_ifc_coordinate_reference_system_uro_name xml_buffer, uro_ifc_boundary_surface_attribute{}.uro_ifc_map_conversion_uro_target_crs_uro_ifc_coordinate_reference_system_uro_description xml_buffer, uro_ifc_boundary_surface_attribute{}.uro_ifc_map_conversion_uro_target_crs_uro_ifc_coordinate_reference_system_uro_geodetic_datum xml_buffer, uro_ifc_boundary_surface_attribute{}.uro_ifc_map_conversion_uro_target_crs_uro_ifc_coordinate_reference_system_uro_vertical_datum xml_buffer, uro_ifc_boundary_surface_attribute{}.uro_ifc_map_conversion_uro_eastings xml_buffer, uro_ifc_boundary_surface_attribute{}.uro_ifc_map_conversion_uro_northings xml_buffer, uro_ifc_boundary_surface_attribute{}.uro_ifc_map_conversion_uro_orthogonal_height xml_real64, uro_ifc_boundary_surface_attribute{}.uro_ifc_map_conversion_uro_orthogonal_height_units xml_buffer, uro_ifc_boundary_surface_attribute{}.uro_ifc_map_conversion_uro_x_axis_abscissa xml_real64, uro_ifc_boundary_surface_attribute{}.uro_ifc_map_conversion_uro_x_axis_ordinate xml_real64, uro_ifc_boundary_surface_attribute{}.uro_ifc_map_conversion_uro_scale xml_real64, uro_ifc_boundary_surface_attribute{}.uro_ifc_opening_element_uro_global_id xml_buffer, uro_ifc_boundary_surface_attribute{}.uro_ifc_opening_element_uro_name xml_buffer,
      uro_ifc_boundary_surface_attribute{}.uro_ifc_opening_element_uro_description xml_buffer, uro_ifc_boundary_surface_attribute{}.uro_ifc_opening_element_uro_object_type xml_buffer, uro_ifc_boundary_surface_attribute{}.uro_ifc_opening_element_uro_tag xml_buffer, uro_ifc_boundary_surface_attribute{}.uro_ifc_opening_element_uro_nominal_area xml_real64, uro_ifc_boundary_surface_attribute{}.uro_ifc_opening_element_uro_nominal_area_units xml_buffer, uro_ifc_boundary_surface_attribute{}.uro_ifc_opening_element_uro_nominal_volume xml_real64, uro_ifc_boundary_surface_attribute{}.uro_ifc_opening_element_uro_nominal_volume_units xml_buffer, uro_ifc_boundary_surface_attribute{}.uro_ifc_project_uro_global_id xml_buffer, uro_ifc_boundary_surface_attribute{}.uro_ifc_project_uro_name xml_buffer, uro_ifc_boundary_surface_attribute{}.uro_ifc_project_uro_description xml_buffer, uro_ifc_boundary_surface_attribute{}.uro_ifc_project_uro_object_type xml_buffer, uro_ifc_boundary_surface_attribute{}.uro_ifc_project_uro_long_name xml_buffer, uro_ifc_boundary_surface_attribute{}.uro_ifc_project_uro_phase xml_buffer, uro_ifc_boundary_surface_attribute{}.uro_ifc_project_uro_representation_contexts_uro_ifc_geometric_representation_context_uro_context_identifier xml_buffer, uro_ifc_boundary_surface_attribute{}.uro_ifc_project_uro_representation_contexts_uro_ifc_geometric_representation_context_uro_context_type xml_buffer, uro_ifc_boundary_surface_attribute{}.uro_ifc_project_uro_representation_contexts_uro_ifc_geometric_representation_context_uro_coordinate_space_dimension xml_int64, uro_ifc_boundary_surface_attribute{}.uro_ifc_project_uro_representation_contexts_uro_ifc_geometric_representation_context_uro_precision xml_real64, uro_ifc_boundary_surface_attribute{}.uro_ifc_project_uro_representation_contexts_uro_ifc_geometric_representation_context_uro_true_north xml_real64, uro_ifc_boundary_surface_attribute{}.uro_ifc_project_uro_units_in_context{}.uro_ifc_unit_uro_dimensions xml_int64, uro_ifc_boundary_surface_attribute{}.uro_ifc_project_uro_units_in_context{}.uro_ifc_unit_uro_unit_type xml_char(28), uro_ifc_boundary_surface_attribute{}.uro_ifc_project_uro_units_in_context{}.uro_ifc_unit_uro_perfix xml_buffer, uro_ifc_boundary_surface_attribute{}.uro_ifc_project_uro_units_in_context{}.uro_ifc_unit_uro_name xml_buffer, uro_ifc_boundary_surface_attribute{}.uro_ifc_projected_crs_uro_name xml_buffer, uro_ifc_boundary_surface_attribute{}.uro_ifc_projected_crs_uro_description xml_buffer, uro_ifc_boundary_surface_attribute{}.uro_ifc_projected_crs_uro_geodetic_datum xml_buffer, uro_ifc_boundary_surface_attribute{}.uro_ifc_projected_crs_uro_vertical_datum xml_buffer, uro_ifc_boundary_surface_attribute{}.uro_ifc_projected_crs_uro_map_unit xml_buffer, uro_ifc_boundary_surface_attribute{}.uro_ifc_projected_crs_uro_map_projection xml_buffer, uro_ifc_boundary_surface_attribute{}.uro_ifc_projected_crs_uro_map_zone xml_buffer, uro_ifc_boundary_surface_attribute{}.uro_ifc_pset_building_common_uro_building_id xml_real64,
      uro_ifc_boundary_surface_attribute{}.uro_ifc_pset_building_common_uro_building_id_units xml_buffer, uro_ifc_boundary_surface_attribute{}.uro_ifc_pset_building_common_uro_is_permanent_id xml_real64, uro_ifc_boundary_surface_attribute{}.uro_ifc_pset_building_common_uro_is_permanent_id_units xml_buffer, uro_ifc_boundary_surface_attribute{}.uro_ifc_pset_building_common_uro_main_fire_use xml_buffer, uro_ifc_boundary_surface_attribute{}.uro_ifc_pset_building_common_uro_ancillary_fire_use xml_buffer, uro_ifc_boundary_surface_attribute{}.uro_ifc_pset_building_common_uro_sprinkler_protection xml_boolean, uro_ifc_boundary_surface_attribute{}.uro_ifc_pset_building_common_uro_sprinkler_protection_automatic xml_boolean, uro_ifc_boundary_surface_attribute{}.uro_ifc_pset_building_common_uro_occupancy_type xml_buffer, uro_ifc_boundary_surface_attribute{}.uro_ifc_pset_building_common_uro_occupancy_type_codeSpace xml_buffer, uro_ifc_boundary_surface_attribute{}.uro_ifc_pset_building_common_uro_gross_planned_area xml_real64, uro_ifc_boundary_surface_attribute{}.uro_ifc_pset_building_common_uro_gross_planned_area_units xml_buffer, uro_ifc_boundary_surface_attribute{}.uro_ifc_pset_building_common_uro_number_of_storeys xml_int64, uro_ifc_boundary_surface_attribute{}.uro_ifc_pset_building_common_uro_year_of_construction xml_buffer, uro_ifc_boundary_surface_attribute{}.uro_ifc_pset_building_common_uro_is_landmarked xml_boolean, uro_ifc_boundary_surface_attribute{}.uro_ifc_pset_door_common_uro_reference xml_buffer, uro_ifc_boundary_surface_attribute{}.uro_ifc_pset_door_common_uro_acoustic_rating xml_buffer, uro_ifc_boundary_surface_attribute{}.uro_ifc_pset_door_common_uro_firerating xml_buffer, uro_ifc_boundary_surface_attribute{}.uro_ifc_pset_door_common_uro_security_rating xml_buffer, uro_ifc_boundary_surface_attribute{}.uro_ifc_pset_door_common_uro_is_external xml_boolean, uro_ifc_boundary_surface_attribute{}.uro_ifc_pset_door_common_uro_infiltration xml_real64, uro_ifc_boundary_surface_attribute{}.uro_ifc_pset_door_common_uro_thermal_transmittance xml_real64, uro_ifc_boundary_surface_attribute{}.uro_ifc_pset_door_common_uro_glazing_area_fraction xml_real64, uro_ifc_boundary_surface_attribute{}.uro_ifc_pset_door_common_uro_handicap_accessible xml_real64, uro_ifc_boundary_surface_attribute{}.uro_ifc_pset_door_common_uro_fire_exit xml_boolean, uro_ifc_boundary_surface_attribute{}.uro_ifc_pset_door_common_uro_self_closing xml_real64, uro_ifc_boundary_surface_attribute{}.uro_ifc_pset_door_common_uro_smoke_stop xml_boolean, uro_ifc_boundary_surface_attribute{}.uro_ifc_pset_opening_element_common_uro_reference xml_buffer, uro_ifc_boundary_surface_attribute{}.uro_ifc_pset_opening_element_common_uro_purpose xml_buffer, uro_ifc_boundary_surface_attribute{}.uro_ifc_pset_opening_element_common_uro_fire_exit xml_boolean, uro_ifc_boundary_surface_attribute{}.uro_ifc_pset_opening_element_common_uro_protected_opening xml_boolean,
      uro_ifc_boundary_surface_attribute{}.uro_ifc_pset_opening_element_common_uro_parallel_jambs xml_boolean, uro_ifc_boundary_surface_attribute{}.uro_ifc_pset_site_common_uro_buildable_area xml_real64, uro_ifc_boundary_surface_attribute{}.uro_ifc_pset_site_common_uro_buildable_area_units xml_buffer, uro_ifc_boundary_surface_attribute{}.uro_ifc_pset_site_common_uro_total_area xml_real64, uro_ifc_boundary_surface_attribute{}.uro_ifc_pset_site_common_uro_total_area_units xml_buffer, uro_ifc_boundary_surface_attribute{}.uro_ifc_pset_site_common_uro_building_height_limit xml_real64, uro_ifc_boundary_surface_attribute{}.uro_ifc_pset_site_common_uro_building_height_limit_units xml_buffer, uro_ifc_boundary_surface_attribute{}.uro_ifc_pset_space_common_uro_reference xml_buffer, uro_ifc_boundary_surface_attribute{}.uro_ifc_pset_space_common_uro_category xml_buffer, uro_ifc_boundary_surface_attribute{}.uro_ifc_pset_space_common_uro_category_codeSpace xml_buffer, uro_ifc_boundary_surface_attribute{}.uro_ifc_pset_space_common_uro_floor_covering xml_buffer, uro_ifc_boundary_surface_attribute{}.uro_ifc_pset_space_common_uro_wall_covering xml_buffer, uro_ifc_boundary_surface_attribute{}.uro_ifc_pset_space_common_uro_ceiling_covering xml_buffer, uro_ifc_boundary_surface_attribute{}.uro_ifc_pset_space_common_uro_skirting_covering xml_buffer, uro_ifc_boundary_surface_attribute{}.uro_ifc_pset_space_common_uro_gross_planned_area xml_real64, uro_ifc_boundary_surface_attribute{}.uro_ifc_pset_space_common_uro_gross_planned_area_units xml_buffer, uro_ifc_boundary_surface_attribute{}.uro_ifc_pset_space_common_uro_net_planned_area xml_real64, uro_ifc_boundary_surface_attribute{}.uro_ifc_pset_space_common_uro_net_planned_area_units xml_buffer, uro_ifc_boundary_surface_attribute{}.uro_ifc_pset_space_common_uro_publicly_accessible xml_boolean, uro_ifc_boundary_surface_attribute{}.uro_ifc_pset_space_common_uro_handicap_accessible xml_boolean, uro_ifc_boundary_surface_attribute{}.uro_ifc_pset_space_common_uro_concealed_flooring xml_boolean, uro_ifc_boundary_surface_attribute{}.uro_ifc_pset_space_common_uro_concealed_ceiling xml_boolean, uro_ifc_boundary_surface_attribute{}.uro_ifc_pset_window_common_uro_reference xml_buffer, uro_ifc_boundary_surface_attribute{}.uro_ifc_pset_window_common_uro_acoustic_rating xml_buffer, uro_ifc_boundary_surface_attribute{}.uro_ifc_pset_window_common_uro_firerating xml_buffer, uro_ifc_boundary_surface_attribute{}.uro_ifc_pset_window_common_uro_security_rating xml_buffer, uro_ifc_boundary_surface_attribute{}.uro_ifc_pset_window_common_uro_is_external xml_boolean, uro_ifc_boundary_surface_attribute{}.uro_ifc_pset_window_common_uro_infiltration xml_real64, uro_ifc_boundary_surface_attribute{}.uro_ifc_pset_window_common_uro_thermal_transmittance xml_real64, uro_ifc_boundary_surface_attribute{}.uro_ifc_pset_window_common_uro_glazing_area_fraction xml_real64,
      uro_ifc_boundary_surface_attribute{}.uro_ifc_pset_window_common_uro_smoke_stop xml_boolean, uro_ifc_boundary_surface_attribute{}.uro_ifc_site_uro_global_id xml_buffer, uro_ifc_boundary_surface_attribute{}.uro_ifc_site_uro_name xml_buffer, uro_ifc_boundary_surface_attribute{}.uro_ifc_site_uro_description xml_buffer, uro_ifc_boundary_surface_attribute{}.uro_ifc_site_uro_object_type xml_buffer, uro_ifc_boundary_surface_attribute{}.uro_ifc_site_uro_long_name xml_buffer, uro_ifc_boundary_surface_attribute{}.uro_ifc_site_uro_composition_type xml_char(7), uro_ifc_boundary_surface_attribute{}.uro_ifc_site_uro_ref_longitude xml_real64, uro_ifc_boundary_surface_attribute{}.uro_ifc_site_uro_ref_latitude xml_real64, uro_ifc_boundary_surface_attribute{}.uro_ifc_site_uro_ref_elevation xml_real64, uro_ifc_boundary_surface_attribute{}.uro_ifc_site_uro_ref_elevation_units xml_buffer, uro_ifc_boundary_surface_attribute{}.uro_ifc_site_uro_land_title_number xml_buffer, uro_ifc_boundary_surface_attribute{}.uro_ifc_site_uro_site_address_xlink_href xml_buffer, uro_ifc_boundary_surface_attribute{}.uro_ifc_space_uro_global_id xml_buffer, uro_ifc_boundary_surface_attribute{}.uro_ifc_space_uro_name xml_buffer, uro_ifc_boundary_surface_attribute{}.uro_ifc_space_uro_description xml_buffer, uro_ifc_boundary_surface_attribute{}.uro_ifc_space_uro_object_type xml_buffer, uro_ifc_boundary_surface_attribute{}.uro_ifc_space_uro_long_name xml_buffer, uro_ifc_boundary_surface_attribute{}.uro_ifc_space_uro_composition_type xml_char(7), uro_ifc_boundary_surface_attribute{}.uro_ifc_space_uro_interioror_exterior_space xml_char(10), uro_ifc_boundary_surface_attribute{}.uro_ifc_space_uro_elevation_with_flooring xml_real64, uro_ifc_boundary_surface_attribute{}.uro_ifc_space_uro_elevation_with_flooring_units xml_buffer, uro_ifc_boundary_surface_attribute{}.uro_ifc_space_base_quantity_uro_nominal_height xml_real64, uro_ifc_boundary_surface_attribute{}.uro_ifc_space_base_quantity_uro_nominal_height_units xml_buffer, uro_ifc_boundary_surface_attribute{}.uro_ifc_space_base_quantity_uro_clear_height xml_real64, uro_ifc_boundary_surface_attribute{}.uro_ifc_space_base_quantity_uro_clear_height_units xml_buffer, uro_ifc_boundary_surface_attribute{}.uro_ifc_space_base_quantity_uro_finish_ceiling_height xml_real64, uro_ifc_boundary_surface_attribute{}.uro_ifc_space_base_quantity_uro_finish_ceiling_height_units xml_buffer, uro_ifc_boundary_surface_attribute{}.uro_ifc_space_base_quantity_uro_gross_perimeter xml_real64, uro_ifc_boundary_surface_attribute{}.uro_ifc_space_base_quantity_uro_gross_perimeter_units xml_buffer,
      uro_ifc_boundary_surface_attribute{}.uro_ifc_space_base_quantity_uro_net_perimeter xml_real64, uro_ifc_boundary_surface_attribute{}.uro_ifc_space_base_quantity_uro_net_perimeter_units xml_buffer, uro_ifc_boundary_surface_attribute{}.uro_ifc_space_base_quantity_uro_gross_ceiling_area xml_real64, uro_ifc_boundary_surface_attribute{}.uro_ifc_space_base_quantity_uro_gross_ceiling_area_units xml_buffer, uro_ifc_boundary_surface_attribute{}.uro_ifc_space_base_quantity_uro_gross_floor_area xml_real64, uro_ifc_boundary_surface_attribute{}.uro_ifc_space_base_quantity_uro_gross_floor_area_units xml_buffer, uro_ifc_boundary_surface_attribute{}.uro_ifc_space_base_quantity_uro_net_ceiling_area xml_real64, uro_ifc_boundary_surface_attribute{}.uro_ifc_space_base_quantity_uro_net_ceiling_area_units xml_buffer, uro_ifc_boundary_surface_attribute{}.uro_ifc_space_base_quantity_uro_net_floor_area xml_real64, uro_ifc_boundary_surface_attribute{}.uro_ifc_space_base_quantity_uro_net_floor_area_units xml_buffer, uro_ifc_boundary_surface_attribute{}.uro_ifc_space_base_quantity_uro_gross_wall_area xml_real64, uro_ifc_boundary_surface_attribute{}.uro_ifc_space_base_quantity_uro_gross_wall_area_units xml_buffer, uro_ifc_boundary_surface_attribute{}.uro_ifc_space_base_quantity_uro_net_wall_area xml_real64, uro_ifc_boundary_surface_attribute{}.uro_ifc_space_base_quantity_uro_net_wall_area_units xml_buffer, uro_ifc_boundary_surface_attribute{}.uro_ifc_space_base_quantity_uro_gross_volume xml_real64, uro_ifc_boundary_surface_attribute{}.uro_ifc_space_base_quantity_uro_gross_volume_units xml_buffer, uro_ifc_boundary_surface_attribute{}.uro_ifc_space_base_quantity_uro_net_volume xml_real64, uro_ifc_boundary_surface_attribute{}.uro_ifc_space_base_quantity_uro_net_volume_units xml_buffer, uro_ifc_boundary_surface_attribute{}.uro_ifc_wall_uro_global_id xml_buffer, uro_ifc_boundary_surface_attribute{}.uro_ifc_wall_uro_name xml_buffer, uro_ifc_boundary_surface_attribute{}.uro_ifc_wall_uro_description xml_buffer, uro_ifc_boundary_surface_attribute{}.uro_ifc_wall_uro_object_type xml_buffer, uro_ifc_boundary_surface_attribute{}.uro_ifc_wall_uro_tag xml_buffer, uro_ifc_boundary_surface_attribute{}.uro_ifc_wall_uro_element_type xml_buffer, uro_ifc_boundary_surface_attribute{}.uro_ifc_wall_uro_element_type_codeSpace xml_buffer, uro_ifc_boundary_surface_attribute{}.uro_ifc_wall_uro_predefined_type xml_buffer, uro_ifc_boundary_surface_attribute{}.uro_ifc_wall_uro_predefined_type_codeSpace xml_buffer, uro_ifc_boundary_surface_attribute{}.uro_ifc_wall_uro_shape_type xml_buffer, uro_ifc_boundary_surface_attribute{}.uro_ifc_wall_uro_shape_type_codeSpace xml_buffer, uro_ifc_boundary_surface_attribute{}.uro_ifc_wall_uro_number_of_riser xml_int64,
      uro_ifc_boundary_surface_attribute{}.uro_ifc_wall_uro_number_of_treads xml_int64, uro_ifc_boundary_surface_attribute{}.uro_ifc_wall_uro_riser_height xml_int64, uro_ifc_boundary_surface_attribute{}.uro_ifc_wall_uro_tread_length xml_int64, uro_ifc_boundary_surface_attribute{}.uro_ifc_wall_uro_operation_type xml_char(11), uro_ifc_boundary_surface_attribute{}.uro_ifc_wall_uro_capacity_by_weight xml_real64, uro_ifc_boundary_surface_attribute{}.uro_ifc_wall_uro_capacity_by_weight_units xml_buffer, uro_ifc_boundary_surface_attribute{}.uro_ifc_wall_uro_capacity_by_number xml_int64, uro_ifc_boundary_surface_attribute{}.uro_ifc_wall_uro_nominal_length xml_real64, uro_ifc_boundary_surface_attribute{}.uro_ifc_wall_uro_nominal_length_units xml_buffer, uro_ifc_boundary_surface_attribute{}.uro_ifc_wall_uro_nominal_width xml_real64, uro_ifc_boundary_surface_attribute{}.uro_ifc_wall_uro_nominal_width_units xml_buffer, uro_ifc_boundary_surface_attribute{}.uro_ifc_wall_uro_nominal_height xml_real64, uro_ifc_boundary_surface_attribute{}.uro_ifc_wall_uro_nominal_height_units xml_buffer, uro_ifc_boundary_surface_attribute{}.uro_ifc_wall_uro_gross_foot_print_area xml_real64, uro_ifc_boundary_surface_attribute{}.uro_ifc_wall_uro_gross_foot_print_area_units xml_buffer, uro_ifc_boundary_surface_attribute{}.uro_ifc_wall_uro_net_foot_print_area xml_real64, uro_ifc_boundary_surface_attribute{}.uro_ifc_wall_uro_net_foot_print_area_units xml_buffer, uro_ifc_boundary_surface_attribute{}.uro_ifc_wall_uro_gross_side_area xml_real64, uro_ifc_boundary_surface_attribute{}.uro_ifc_wall_uro_gross_side_area_units xml_buffer, uro_ifc_boundary_surface_attribute{}.uro_ifc_wall_uro_net_side_area xml_real64, uro_ifc_boundary_surface_attribute{}.uro_ifc_wall_uro_net_side_area_units xml_buffer, uro_ifc_boundary_surface_attribute{}.uro_ifc_wall_uro_gross_side_area_left xml_real64, uro_ifc_boundary_surface_attribute{}.uro_ifc_wall_uro_gross_side_area_left_units xml_buffer, uro_ifc_boundary_surface_attribute{}.uro_ifc_wall_uro_net_side_area_left xml_real64, uro_ifc_boundary_surface_attribute{}.uro_ifc_wall_uro_net_side_area_left_units xml_buffer, uro_ifc_boundary_surface_attribute{}.uro_ifc_wall_uro_gross_side_area_right xml_real64, uro_ifc_boundary_surface_attribute{}.uro_ifc_wall_uro_gross_side_area_right_units xml_buffer, uro_ifc_boundary_surface_attribute{}.uro_ifc_wall_uro_net_side_area_right xml_real64, uro_ifc_boundary_surface_attribute{}.uro_ifc_wall_uro_net_side_area_right_units xml_buffer, uro_ifc_boundary_surface_attribute{}.uro_ifc_wall_uro_gross_volume xml_real64,
      uro_ifc_boundary_surface_attribute{}.uro_ifc_wall_uro_gross_volume_units xml_buffer, uro_ifc_boundary_surface_attribute{}.uro_ifc_wall_uro_net_volume xml_real64, uro_ifc_boundary_surface_attribute{}.uro_ifc_wall_uro_net_volume_units xml_buffer, uro_ifc_boundary_surface_attribute{}.uro_ifc_wall_standard_case_uro_global_id xml_buffer, uro_ifc_boundary_surface_attribute{}.uro_ifc_wall_standard_case_uro_name xml_buffer, uro_ifc_boundary_surface_attribute{}.uro_ifc_wall_standard_case_uro_description xml_buffer, uro_ifc_boundary_surface_attribute{}.uro_ifc_wall_standard_case_uro_object_type xml_buffer, uro_ifc_boundary_surface_attribute{}.uro_ifc_wall_standard_case_uro_tag xml_buffer, uro_ifc_boundary_surface_attribute{}.uro_ifc_wall_standard_case_uro_element_type xml_buffer, uro_ifc_boundary_surface_attribute{}.uro_ifc_wall_standard_case_uro_element_type_codeSpace xml_buffer, uro_ifc_boundary_surface_attribute{}.uro_ifc_wall_standard_case_uro_predefined_type xml_buffer, uro_ifc_boundary_surface_attribute{}.uro_ifc_wall_standard_case_uro_predefined_type_codeSpace xml_buffer, uro_ifc_boundary_surface_attribute{}.uro_ifc_wall_standard_case_uro_shape_type xml_buffer, uro_ifc_boundary_surface_attribute{}.uro_ifc_wall_standard_case_uro_shape_type_codeSpace xml_buffer, uro_ifc_boundary_surface_attribute{}.uro_ifc_wall_standard_case_uro_number_of_riser xml_int64, uro_ifc_boundary_surface_attribute{}.uro_ifc_wall_standard_case_uro_number_of_treads xml_int64, uro_ifc_boundary_surface_attribute{}.uro_ifc_wall_standard_case_uro_riser_height xml_int64, uro_ifc_boundary_surface_attribute{}.uro_ifc_wall_standard_case_uro_tread_length xml_int64, uro_ifc_boundary_surface_attribute{}.uro_ifc_wall_standard_case_uro_operation_type xml_char(11), uro_ifc_boundary_surface_attribute{}.uro_ifc_wall_standard_case_uro_capacity_by_weight xml_real64, uro_ifc_boundary_surface_attribute{}.uro_ifc_wall_standard_case_uro_capacity_by_weight_units xml_buffer, uro_ifc_boundary_surface_attribute{}.uro_ifc_wall_standard_case_uro_capacity_by_number xml_int64, uro_ifc_boundary_surface_attribute{}.uro_ifc_wall_standard_case_uro_nominal_length xml_real64, uro_ifc_boundary_surface_attribute{}.uro_ifc_wall_standard_case_uro_nominal_length_units xml_buffer, uro_ifc_boundary_surface_attribute{}.uro_ifc_wall_standard_case_uro_nominal_width xml_real64, uro_ifc_boundary_surface_attribute{}.uro_ifc_wall_standard_case_uro_nominal_width_units xml_buffer, uro_ifc_boundary_surface_attribute{}.uro_ifc_wall_standard_case_uro_nominal_height xml_real64, uro_ifc_boundary_surface_attribute{}.uro_ifc_wall_standard_case_uro_nominal_height_units xml_buffer, uro_ifc_boundary_surface_attribute{}.uro_ifc_wall_standard_case_uro_gross_foot_print_area xml_real64, uro_ifc_boundary_surface_attribute{}.uro_ifc_wall_standard_case_uro_gross_foot_print_area_units xml_buffer,
      uro_ifc_boundary_surface_attribute{}.uro_ifc_wall_standard_case_uro_net_foot_print_area xml_real64, uro_ifc_boundary_surface_attribute{}.uro_ifc_wall_standard_case_uro_net_foot_print_area_units xml_buffer, uro_ifc_boundary_surface_attribute{}.uro_ifc_wall_standard_case_uro_gross_side_area xml_real64, uro_ifc_boundary_surface_attribute{}.uro_ifc_wall_standard_case_uro_gross_side_area_units xml_buffer, uro_ifc_boundary_surface_attribute{}.uro_ifc_wall_standard_case_uro_net_side_area xml_real64, uro_ifc_boundary_surface_attribute{}.uro_ifc_wall_standard_case_uro_net_side_area_units xml_buffer, uro_ifc_boundary_surface_attribute{}.uro_ifc_wall_standard_case_uro_gross_side_area_left xml_real64, uro_ifc_boundary_surface_attribute{}.uro_ifc_wall_standard_case_uro_gross_side_area_left_units xml_buffer, uro_ifc_boundary_surface_attribute{}.uro_ifc_wall_standard_case_uro_net_side_area_left xml_real64, uro_ifc_boundary_surface_attribute{}.uro_ifc_wall_standard_case_uro_net_side_area_left_units xml_buffer, uro_ifc_boundary_surface_attribute{}.uro_ifc_wall_standard_case_uro_gross_side_area_right xml_real64, uro_ifc_boundary_surface_attribute{}.uro_ifc_wall_standard_case_uro_gross_side_area_right_units xml_buffer, uro_ifc_boundary_surface_attribute{}.uro_ifc_wall_standard_case_uro_net_side_area_right xml_real64, uro_ifc_boundary_surface_attribute{}.uro_ifc_wall_standard_case_uro_net_side_area_right_units xml_buffer, uro_ifc_boundary_surface_attribute{}.uro_ifc_wall_standard_case_uro_gross_volume xml_real64, uro_ifc_boundary_surface_attribute{}.uro_ifc_wall_standard_case_uro_gross_volume_units xml_buffer, uro_ifc_boundary_surface_attribute{}.uro_ifc_wall_standard_case_uro_net_volume xml_real64, uro_ifc_boundary_surface_attribute{}.uro_ifc_wall_standard_case_uro_net_volume_units xml_buffer, uro_ifc_boundary_surface_attribute{}.uro_ifc_window_uro_global_id xml_buffer, uro_ifc_boundary_surface_attribute{}.uro_ifc_window_uro_name xml_buffer, uro_ifc_boundary_surface_attribute{}.uro_ifc_window_uro_description xml_buffer, uro_ifc_boundary_surface_attribute{}.uro_ifc_window_uro_object_type xml_buffer, uro_ifc_boundary_surface_attribute{}.uro_ifc_window_uro_tag xml_buffer, uro_ifc_boundary_surface_attribute{}.uro_ifc_window_uro_element_type xml_buffer, uro_ifc_boundary_surface_attribute{}.uro_ifc_window_uro_element_type_codeSpace xml_buffer, uro_ifc_boundary_surface_attribute{}.uro_ifc_window_uro_predefined_type xml_buffer, uro_ifc_boundary_surface_attribute{}.uro_ifc_window_uro_predefined_type_codeSpace xml_buffer, uro_ifc_boundary_surface_attribute{}.uro_ifc_window_uro_shape_type xml_buffer, uro_ifc_boundary_surface_attribute{}.uro_ifc_window_uro_shape_type_codeSpace xml_buffer, uro_ifc_boundary_surface_attribute{}.uro_ifc_window_uro_number_of_riser xml_int64,
      uro_ifc_boundary_surface_attribute{}.uro_ifc_window_uro_number_of_treads xml_int64, uro_ifc_boundary_surface_attribute{}.uro_ifc_window_uro_riser_height xml_int64, uro_ifc_boundary_surface_attribute{}.uro_ifc_window_uro_tread_length xml_int64, uro_ifc_boundary_surface_attribute{}.uro_ifc_window_uro_operation_type xml_char(11), uro_ifc_boundary_surface_attribute{}.uro_ifc_window_uro_capacity_by_weight xml_real64, uro_ifc_boundary_surface_attribute{}.uro_ifc_window_uro_capacity_by_weight_units xml_buffer, uro_ifc_boundary_surface_attribute{}.uro_ifc_window_uro_capacity_by_number xml_int64, uro_ifc_boundary_surface_attribute{}.uro_ifc_window_uro_overall_height xml_real64, uro_ifc_boundary_surface_attribute{}.uro_ifc_window_uro_overall_height_units xml_buffer, uro_ifc_boundary_surface_attribute{}.uro_ifc_window_uro_overall_width xml_real64, uro_ifc_boundary_surface_attribute{}.uro_ifc_window_uro_overall_width_units xml_buffer
Note: AttributeManager_13 : Input / Room ソリッドに集約
Junction_17
    -> Junction_19
Note: CeilingSurface / AttributeManager_5 : Output
Junction_19
    -> AttributeManager_13
Note: 床: FloorSurface
AttributeManager_6
    ATTR_TABLE:
      SET_TO gml_id = floor_@UUID()
      SET_TO _citygml_feature_type = FloorSurface
      REMOVE _surfaceNormalX
      REMOVE _surfaceNormalY
      REMOVE _surfaceNormalZ
      REMOVE _pointOnSurfaceX
      REMOVE _pointOnSurfaceY
      REMOVE _pointOnSurfaceZ
      SET_TO citygml_lod_name = lod4MultiSurface
      SET_TO citygml_feature_role = boundedBy
    -> GeometryPropertySetter_5
    -> Junction_21
GeometryPropertySetter_5
    GQUERY:
      for $geom in //geometry
      where $geom/count(parent::geometry) = 0
      return number($geom/@fme_id)
    OVERWRITE_CHOICE = Yes
    REMOVE_ATTRIBUTE = Yes
    SETTYPE_PARAM = Traits From Attributes
    SRC_ATTRS = citygml_lod_name gml_id
    SET -> AttributeCreator_7
AttributeCreator_7
    ATTR_TABLE:
      SET_TO gml_id = @Value(_boundary_gml_id)
      SET_TO gml_parent_id = @Value(_room_gml_id)
    -> PLATEAU.IfcReprojector_5 [IfcFeature]
    -> Junction_81
PLATEAU.IfcReprojector_5
    DEST_COORDSYS = $(DEST_COORDSYS)
    LENGTH_MULTIPLIER = @Value(_lengthmultiplier)
    REPROJECTION_PARAMS = @Value(_reprojection_params)
    Reprojected -> FloorSurface (writer CITYGML_2)
FloorSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, uro_ifc_boundary_surface_attribute{}.uro_ifc_building_uro_global_id xml_buffer, uro_ifc_boundary_surface_attribute{}.uro_ifc_building_uro_name xml_buffer, uro_ifc_boundary_surface_attribute{}.uro_ifc_building_uro_description xml_buffer, uro_ifc_boundary_surface_attribute{}.uro_ifc_building_uro_object_type xml_buffer, uro_ifc_boundary_surface_attribute{}.uro_ifc_building_uro_long_name xml_buffer, uro_ifc_boundary_surface_attribute{}.uro_ifc_building_uro_composition_type xml_char(7), uro_ifc_boundary_surface_attribute{}.uro_ifc_building_uro_elevation_of_ref_height xml_real64, uro_ifc_boundary_surface_attribute{}.uro_ifc_building_uro_elevation_of_ref_height_units xml_buffer, uro_ifc_boundary_surface_attribute{}.uro_ifc_building_uro_elevation_of_terrain xml_real64, uro_ifc_boundary_surface_attribute{}.uro_ifc_building_uro_elevation_of_terrain_units xml_buffer, uro_ifc_boundary_surface_attribute{}.uro_ifc_building_uro_building_address_xlink_href xml_buffer, uro_ifc_boundary_surface_attribute{}.uro_ifc_building_element_uro_global_id xml_buffer, uro_ifc_boundary_surface_attribute{}.uro_ifc_building_element_uro_name xml_buffer, uro_ifc_boundary_surface_attribute{}.uro_ifc_building_element_uro_description xml_buffer,
      uro_ifc_boundary_surface_attribute{}.uro_ifc_building_element_uro_object_type xml_buffer, uro_ifc_boundary_surface_attribute{}.uro_ifc_building_element_uro_tag xml_buffer, uro_ifc_boundary_surface_attribute{}.uro_ifc_building_element_uro_element_type xml_buffer, uro_ifc_boundary_surface_attribute{}.uro_ifc_building_element_uro_element_type_codeSpace xml_buffer, uro_ifc_boundary_surface_attribute{}.uro_ifc_building_element_uro_predefined_type xml_buffer, uro_ifc_boundary_surface_attribute{}.uro_ifc_building_element_uro_predefined_type_codeSpace xml_buffer, uro_ifc_boundary_surface_attribute{}.uro_ifc_building_element_uro_shape_type xml_buffer, uro_ifc_boundary_surface_attribute{}.uro_ifc_building_element_uro_shape_type_codeSpace xml_buffer, uro_ifc_boundary_surface_attribute{}.uro_ifc_building_element_uro_number_of_riser xml_int64, uro_ifc_boundary_surface_attribute{}.uro_ifc_building_element_uro_number_of_treads xml_int64, uro_ifc_boundary_surface_attribute{}.uro_ifc_building_element_uro_riser_height xml_int64, uro_ifc_boundary_surface_attribute{}.uro_ifc_building_element_uro_tread_length xml_int64, uro_ifc_boundary_surface_attribute{}.uro_ifc_building_element_uro_operation_type xml_char(11), uro_ifc_boundary_surface_attribute{}.uro_ifc_building_element_uro_capacity_by_weight xml_real64, uro_ifc_boundary_surface_attribute{}.uro_ifc_building_element_uro_capacity_by_weight_units xml_buffer, uro_ifc_boundary_surface_attribute{}.uro_ifc_building_element_uro_capacity_by_number xml_int64, uro_ifc_boundary_surface_attribute{}.uro_ifc_building_storey_uro_global_id xml_buffer, uro_ifc_boundary_surface_attribute{}.uro_ifc_building_storey_uro_name xml_buffer, uro_ifc_boundary_surface_attribute{}.uro_ifc_building_storey_uro_description xml_buffer, uro_ifc_boundary_surface_attribute{}.uro_ifc_building_storey_uro_object_type xml_buffer, uro_ifc_boundary_surface_attribute{}.uro_ifc_building_storey_uro_long_name xml_buffer, uro_ifc_boundary_surface_attribute{}.uro_ifc_building_storey_uro_composition_type xml_char(7), uro_ifc_boundary_surface_attribute{}.uro_ifc_building_storey_uro_elevation xml_real64, uro_ifc_boundary_surface_attribute{}.uro_ifc_building_storey_uro_elevation_units xml_buffer, uro_ifc_boundary_surface_attribute{}.uro_ifc_classification_reference_uro_location xml_buffer, uro_ifc_boundary_surface_attribute{}.uro_ifc_classification_reference_uro_item_reference xml_buffer, uro_ifc_boundary_surface_attribute{}.uro_ifc_classification_reference_uro_item_reference_codeSpace xml_buffer, uro_ifc_boundary_surface_attribute{}.uro_ifc_classification_reference_uro_name xml_buffer, uro_ifc_boundary_surface_attribute{}.uro_ifc_classification_reference_uro_name_codeSpace xml_buffer, uro_ifc_boundary_surface_attribute{}.uro_ifc_classification_reference_uro_reference_source_uro_ifc_classification_uro_source xml_buffer,
      uro_ifc_boundary_surface_attribute{}.uro_ifc_classification_reference_uro_reference_source_uro_ifc_classification_uro_edition xml_buffer, uro_ifc_boundary_surface_attribute{}.uro_ifc_classification_reference_uro_reference_source_uro_ifc_classification_uro_edition_date xml_date, uro_ifc_boundary_surface_attribute{}.uro_ifc_classification_reference_uro_reference_source_uro_ifc_classification_uro_name xml_buffer, uro_ifc_boundary_surface_attribute{}.uro_ifc_coordinate_reference_system_uro_name xml_buffer, uro_ifc_boundary_surface_attribute{}.uro_ifc_coordinate_reference_system_uro_description xml_buffer, uro_ifc_boundary_surface_attribute{}.uro_ifc_coordinate_reference_system_uro_geodetic_datum xml_buffer, uro_ifc_boundary_surface_attribute{}.uro_ifc_coordinate_reference_system_uro_vertical_datum xml_buffer, uro_ifc_boundary_surface_attribute{}.uro_ifc_curtain_wall_uro_global_id xml_buffer, uro_ifc_boundary_surface_attribute{}.uro_ifc_curtain_wall_uro_name xml_buffer, uro_ifc_boundary_surface_attribute{}.uro_ifc_curtain_wall_uro_description xml_buffer, uro_ifc_boundary_surface_attribute{}.uro_ifc_curtain_wall_uro_object_type xml_buffer, uro_ifc_boundary_surface_attribute{}.uro_ifc_curtain_wall_uro_tag xml_buffer, uro_ifc_boundary_surface_attribute{}.uro_ifc_curtain_wall_uro_element_type xml_buffer, uro_ifc_boundary_surface_attribute{}.uro_ifc_curtain_wall_uro_element_type_codeSpace xml_buffer, uro_ifc_boundary_surface_attribute{}.uro_ifc_curtain_wall_uro_predefined_type xml_buffer, uro_ifc_boundary_surface_attribute{}.uro_ifc_curtain_wall_uro_predefined_type_codeSpace xml_buffer, uro_ifc_boundary_surface_attribute{}.uro_ifc_curtain_wall_uro_shape_type xml_buffer, uro_ifc_boundary_surface_attribute{}.uro_ifc_curtain_wall_uro_shape_type_codeSpace xml_buffer, uro_ifc_boundary_surface_attribute{}.uro_ifc_curtain_wall_uro_number_of_riser xml_int64, uro_ifc_boundary_surface_attribute{}.uro_ifc_curtain_wall_uro_number_of_treads xml_int64, uro_ifc_boundary_surface_attribute{}.uro_ifc_curtain_wall_uro_riser_height xml_int64, uro_ifc_boundary_surface_attribute{}.uro_ifc_curtain_wall_uro_tread_length xml_int64, uro_ifc_boundary_surface_attribute{}.uro_ifc_curtain_wall_uro_operation_type xml_char(11), uro_ifc_boundary_surface_attribute{}.uro_ifc_curtain_wall_uro_capacity_by_weight xml_real64, uro_ifc_boundary_surface_attribute{}.uro_ifc_curtain_wall_uro_capacity_by_weight_units xml_buffer, uro_ifc_boundary_surface_attribute{}.uro_ifc_curtain_wall_uro_capacity_by_number xml_int64, uro_ifc_boundary_surface_attribute{}.uro_ifc_door_uro_global_id xml_buffer, uro_ifc_boundary_surface_attribute{}.uro_ifc_door_uro_name xml_buffer, uro_ifc_boundary_surface_attribute{}.uro_ifc_door_uro_description xml_buffer, uro_ifc_boundary_surface_attribute{}.uro_ifc_door_uro_object_type xml_buffer,
      uro_ifc_boundary_surface_attribute{}.uro_ifc_door_uro_tag xml_buffer, uro_ifc_boundary_surface_attribute{}.uro_ifc_door_uro_element_type xml_buffer, uro_ifc_boundary_surface_attribute{}.uro_ifc_door_uro_element_type_codeSpace xml_buffer, uro_ifc_boundary_surface_attribute{}.uro_ifc_door_uro_predefined_type xml_buffer, uro_ifc_boundary_surface_attribute{}.uro_ifc_door_uro_predefined_type_codeSpace xml_buffer, uro_ifc_boundary_surface_attribute{}.uro_ifc_door_uro_shape_type xml_buffer, uro_ifc_boundary_surface_attribute{}.uro_ifc_door_uro_shape_type_codeSpace xml_buffer, uro_ifc_boundary_surface_attribute{}.uro_ifc_door_uro_number_of_riser xml_int64, uro_ifc_boundary_surface_attribute{}.uro_ifc_door_uro_number_of_treads xml_int64, uro_ifc_boundary_surface_attribute{}.uro_ifc_door_uro_riser_height xml_int64, uro_ifc_boundary_surface_attribute{}.uro_ifc_door_uro_tread_length xml_int64, uro_ifc_boundary_surface_attribute{}.uro_ifc_door_uro_operation_type xml_char(11), uro_ifc_boundary_surface_attribute{}.uro_ifc_door_uro_capacity_by_weight xml_real64, uro_ifc_boundary_surface_attribute{}.uro_ifc_door_uro_capacity_by_weight_units xml_buffer, uro_ifc_boundary_surface_attribute{}.uro_ifc_door_uro_capacity_by_number xml_int64, uro_ifc_boundary_surface_attribute{}.uro_ifc_door_uro_overall_height xml_real64, uro_ifc_boundary_surface_attribute{}.uro_ifc_door_uro_overall_height_units xml_buffer, uro_ifc_boundary_surface_attribute{}.uro_ifc_door_uro_overall_width xml_real64, uro_ifc_boundary_surface_attribute{}.uro_ifc_door_uro_overall_width_units xml_buffer, uro_ifc_boundary_surface_attribute{}.uro_ifc_furnishing_element_uro_global_id xml_buffer, uro_ifc_boundary_surface_attribute{}.uro_ifc_furnishing_element_uro_name xml_buffer, uro_ifc_boundary_surface_attribute{}.uro_ifc_furnishing_element_uro_description xml_buffer, uro_ifc_boundary_surface_attribute{}.uro_ifc_furnishing_element_uro_object_type xml_buffer, uro_ifc_boundary_surface_attribute{}.uro_ifc_furnishing_element_uro_tag xml_buffer, uro_ifc_boundary_surface_attribute{}.uro_ifc_map_conversion_uro_source_crs_uro_crs_uro_ifc_projected_crs_uro_name xml_buffer, uro_ifc_boundary_surface_attribute{}.uro_ifc_map_conversion_uro_source_crs_uro_crs_uro_ifc_projected_crs_uro_description xml_buffer, uro_ifc_boundary_surface_attribute{}.uro_ifc_map_conversion_uro_source_crs_uro_crs_uro_ifc_projected_crs_uro_geodetic_datum xml_buffer, uro_ifc_boundary_surface_attribute{}.uro_ifc_map_conversion_uro_source_crs_uro_crs_uro_ifc_projected_crs_uro_vertical_datum xml_buffer, uro_ifc_boundary_surface_attribute{}.uro_ifc_map_conversion_uro_source_crs_uro_crs_uro_ifc_projected_crs_uro_map_unit xml_buffer, uro_ifc_boundary_surface_attribute{}.uro_ifc_map_conversion_uro_source_crs_uro_crs_uro_ifc_projected_crs_uro_map_projection xml_buffer,
      uro_ifc_boundary_surface_attribute{}.uro_ifc_map_conversion_uro_source_crs_uro_crs_uro_ifc_projected_crs_uro_map_zone xml_buffer, uro_ifc_boundary_surface_attribute{}.uro_ifc_map_conversion_uro_source_crs_uro_crs_uro_ifc_coordinate_reference_system_uro_name xml_buffer, uro_ifc_boundary_surface_attribute{}.uro_ifc_map_conversion_uro_source_crs_uro_crs_uro_ifc_coordinate_reference_system_uro_description xml_buffer, uro_ifc_boundary_surface_attribute{}.uro_ifc_map_conversion_uro_source_crs_uro_crs_uro_ifc_coordinate_reference_system_uro_geodetic_datum xml_buffer, uro_ifc_boundary_surface_attribute{}.uro_ifc_map_conversion_uro_source_crs_uro_crs_uro_ifc_coordinate_reference_system_uro_vertical_datum xml_buffer, uro_ifc_boundary_surface_attribute{}.uro_ifc_map_conversion_uro_source_crs_uro_context_uro_ifc_geometric_representation_context_uro_context_identifier xml_buffer, uro_ifc_boundary_surface_attribute{}.uro_ifc_map_conversion_uro_source_crs_uro_context_uro_ifc_geometric_representation_context_uro_context_type xml_buffer, uro_ifc_boundary_surface_attribute{}.uro_ifc_map_conversion_uro_source_crs_uro_context_uro_ifc_geometric_representation_context_uro_coordinate_space_dimension xml_int64, uro_ifc_boundary_surface_attribute{}.uro_ifc_map_conversion_uro_source_crs_uro_context_uro_ifc_geometric_representation_context_uro_precision xml_real64, uro_ifc_boundary_surface_attribute{}.uro_ifc_map_conversion_uro_source_crs_uro_context_uro_ifc_geometric_representation_context_uro_true_north xml_real64, uro_ifc_boundary_surface_attribute{}.uro_ifc_map_conversion_uro_target_crs_uro_ifc_projected_crs_uro_name xml_buffer, uro_ifc_boundary_surface_attribute{}.uro_ifc_map_conversion_uro_target_crs_uro_ifc_projected_crs_uro_description xml_buffer, uro_ifc_boundary_surface_attribute{}.uro_ifc_map_conversion_uro_target_crs_uro_ifc_projected_crs_uro_geodetic_datum xml_buffer, uro_ifc_boundary_surface_attribute{}.uro_ifc_map_conversion_uro_target_crs_uro_ifc_projected_crs_uro_vertical_datum xml_buffer, uro_ifc_boundary_surface_attribute{}.uro_ifc_map_conversion_uro_target_crs_uro_ifc_projected_crs_uro_map_unit xml_buffer, uro_ifc_boundary_surface_attribute{}.uro_ifc_map_conversion_uro_target_crs_uro_ifc_projected_crs_uro_map_projection xml_buffer, uro_ifc_boundary_surface_attribute{}.uro_ifc_map_conversion_uro_target_crs_uro_ifc_projected_crs_uro_map_zone xml_buffer, uro_ifc_boundary_surface_attribute{}.uro_ifc_map_conversion_uro_target_crs_uro_ifc_coordinate_reference_system_uro_name xml_buffer, uro_ifc_boundary_surface_attribute{}.uro_ifc_map_conversion_uro_target_crs_uro_ifc_coordinate_reference_system_uro_description xml_buffer, uro_ifc_boundary_surface_attribute{}.uro_ifc_map_conversion_uro_target_crs_uro_ifc_coordinate_reference_system_uro_geodetic_datum xml_buffer, uro_ifc_boundary_surface_attribute{}.uro_ifc_map_conversion_uro_target_crs_uro_ifc_coordinate_reference_system_uro_vertical_datum xml_buffer, uro_ifc_boundary_surface_attribute{}.uro_ifc_map_conversion_uro_eastings xml_buffer, uro_ifc_boundary_surface_attribute{}.uro_ifc_map_conversion_uro_northings xml_buffer, uro_ifc_boundary_surface_attribute{}.uro_ifc_map_conversion_uro_orthogonal_height xml_real64, uro_ifc_boundary_surface_attribute{}.uro_ifc_map_conversion_uro_orthogonal_height_units xml_buffer, uro_ifc_boundary_surface_attribute{}.uro_ifc_map_conversion_uro_x_axis_abscissa xml_real64, uro_ifc_boundary_surface_attribute{}.uro_ifc_map_conversion_uro_x_axis_ordinate xml_real64, uro_ifc_boundary_surface_attribute{}.uro_ifc_map_conversion_uro_scale xml_real64, uro_ifc_boundary_surface_attribute{}.uro_ifc_opening_element_uro_global_id xml_buffer, uro_ifc_boundary_surface_attribute{}.uro_ifc_opening_element_uro_name xml_buffer,
      uro_ifc_boundary_surface_attribute{}.uro_ifc_opening_element_uro_description xml_buffer, uro_ifc_boundary_surface_attribute{}.uro_ifc_opening_element_uro_object_type xml_buffer, uro_ifc_boundary_surface_attribute{}.uro_ifc_opening_element_uro_tag xml_buffer, uro_ifc_boundary_surface_attribute{}.uro_ifc_opening_element_uro_nominal_area xml_real64, uro_ifc_boundary_surface_attribute{}.uro_ifc_opening_element_uro_nominal_area_units xml_buffer, uro_ifc_boundary_surface_attribute{}.uro_ifc_opening_element_uro_nominal_volume xml_real64, uro_ifc_boundary_surface_attribute{}.uro_ifc_opening_element_uro_nominal_volume_units xml_buffer, uro_ifc_boundary_surface_attribute{}.uro_ifc_project_uro_global_id xml_buffer, uro_ifc_boundary_surface_attribute{}.uro_ifc_project_uro_name xml_buffer, uro_ifc_boundary_surface_attribute{}.uro_ifc_project_uro_description xml_buffer, uro_ifc_boundary_surface_attribute{}.uro_ifc_project_uro_object_type xml_buffer, uro_ifc_boundary_surface_attribute{}.uro_ifc_project_uro_long_name xml_buffer, uro_ifc_boundary_surface_attribute{}.uro_ifc_project_uro_phase xml_buffer, uro_ifc_boundary_surface_attribute{}.uro_ifc_project_uro_representation_contexts_uro_ifc_geometric_representation_context_uro_context_identifier xml_buffer, uro_ifc_boundary_surface_attribute{}.uro_ifc_project_uro_representation_contexts_uro_ifc_geometric_representation_context_uro_context_type xml_buffer, uro_ifc_boundary_surface_attribute{}.uro_ifc_project_uro_representation_contexts_uro_ifc_geometric_representation_context_uro_coordinate_space_dimension xml_int64, uro_ifc_boundary_surface_attribute{}.uro_ifc_project_uro_representation_contexts_uro_ifc_geometric_representation_context_uro_precision xml_real64, uro_ifc_boundary_surface_attribute{}.uro_ifc_project_uro_representation_contexts_uro_ifc_geometric_representation_context_uro_true_north xml_real64, uro_ifc_boundary_surface_attribute{}.uro_ifc_project_uro_units_in_context{}.uro_ifc_unit_uro_dimensions xml_int64, uro_ifc_boundary_surface_attribute{}.uro_ifc_project_uro_units_in_context{}.uro_ifc_unit_uro_unit_type xml_char(28), uro_ifc_boundary_surface_attribute{}.uro_ifc_project_uro_units_in_context{}.uro_ifc_unit_uro_perfix xml_buffer, uro_ifc_boundary_surface_attribute{}.uro_ifc_project_uro_units_in_context{}.uro_ifc_unit_uro_name xml_buffer, uro_ifc_boundary_surface_attribute{}.uro_ifc_projected_crs_uro_name xml_buffer, uro_ifc_boundary_surface_attribute{}.uro_ifc_projected_crs_uro_description xml_buffer, uro_ifc_boundary_surface_attribute{}.uro_ifc_projected_crs_uro_geodetic_datum xml_buffer, uro_ifc_boundary_surface_attribute{}.uro_ifc_projected_crs_uro_vertical_datum xml_buffer, uro_ifc_boundary_surface_attribute{}.uro_ifc_projected_crs_uro_map_unit xml_buffer, uro_ifc_boundary_surface_attribute{}.uro_ifc_projected_crs_uro_map_projection xml_buffer, uro_ifc_boundary_surface_attribute{}.uro_ifc_projected_crs_uro_map_zone xml_buffer, uro_ifc_boundary_surface_attribute{}.uro_ifc_pset_building_common_uro_building_id xml_real64,
      uro_ifc_boundary_surface_attribute{}.uro_ifc_pset_building_common_uro_building_id_units xml_buffer, uro_ifc_boundary_surface_attribute{}.uro_ifc_pset_building_common_uro_is_permanent_id xml_real64, uro_ifc_boundary_surface_attribute{}.uro_ifc_pset_building_common_uro_is_permanent_id_units xml_buffer, uro_ifc_boundary_surface_attribute{}.uro_ifc_pset_building_common_uro_main_fire_use xml_buffer, uro_ifc_boundary_surface_attribute{}.uro_ifc_pset_building_common_uro_ancillary_fire_use xml_buffer, uro_ifc_boundary_surface_attribute{}.uro_ifc_pset_building_common_uro_sprinkler_protection xml_boolean, uro_ifc_boundary_surface_attribute{}.uro_ifc_pset_building_common_uro_sprinkler_protection_automatic xml_boolean, uro_ifc_boundary_surface_attribute{}.uro_ifc_pset_building_common_uro_occupancy_type xml_buffer, uro_ifc_boundary_surface_attribute{}.uro_ifc_pset_building_common_uro_occupancy_type_codeSpace xml_buffer, uro_ifc_boundary_surface_attribute{}.uro_ifc_pset_building_common_uro_gross_planned_area xml_real64, uro_ifc_boundary_surface_attribute{}.uro_ifc_pset_building_common_uro_gross_planned_area_units xml_buffer, uro_ifc_boundary_surface_attribute{}.uro_ifc_pset_building_common_uro_number_of_storeys xml_int64, uro_ifc_boundary_surface_attribute{}.uro_ifc_pset_building_common_uro_year_of_construction xml_buffer, uro_ifc_boundary_surface_attribute{}.uro_ifc_pset_building_common_uro_is_landmarked xml_boolean, uro_ifc_boundary_surface_attribute{}.uro_ifc_pset_door_common_uro_reference xml_buffer, uro_ifc_boundary_surface_attribute{}.uro_ifc_pset_door_common_uro_acoustic_rating xml_buffer, uro_ifc_boundary_surface_attribute{}.uro_ifc_pset_door_common_uro_firerating xml_buffer, uro_ifc_boundary_surface_attribute{}.uro_ifc_pset_door_common_uro_security_rating xml_buffer, uro_ifc_boundary_surface_attribute{}.uro_ifc_pset_door_common_uro_is_external xml_boolean, uro_ifc_boundary_surface_attribute{}.uro_ifc_pset_door_common_uro_infiltration xml_real64, uro_ifc_boundary_surface_attribute{}.uro_ifc_pset_door_common_uro_thermal_transmittance xml_real64, uro_ifc_boundary_surface_attribute{}.uro_ifc_pset_door_common_uro_glazing_area_fraction xml_real64, uro_ifc_boundary_surface_attribute{}.uro_ifc_pset_door_common_uro_handicap_accessible xml_real64, uro_ifc_boundary_surface_attribute{}.uro_ifc_pset_door_common_uro_fire_exit xml_boolean, uro_ifc_boundary_surface_attribute{}.uro_ifc_pset_door_common_uro_self_closing xml_real64, uro_ifc_boundary_surface_attribute{}.uro_ifc_pset_door_common_uro_smoke_stop xml_boolean, uro_ifc_boundary_surface_attribute{}.uro_ifc_pset_opening_element_common_uro_reference xml_buffer, uro_ifc_boundary_surface_attribute{}.uro_ifc_pset_opening_element_common_uro_purpose xml_buffer, uro_ifc_boundary_surface_attribute{}.uro_ifc_pset_opening_element_common_uro_fire_exit xml_boolean, uro_ifc_boundary_surface_attribute{}.uro_ifc_pset_opening_element_common_uro_protected_opening xml_boolean,
      uro_ifc_boundary_surface_attribute{}.uro_ifc_pset_opening_element_common_uro_parallel_jambs xml_boolean, uro_ifc_boundary_surface_attribute{}.uro_ifc_pset_site_common_uro_buildable_area xml_real64, uro_ifc_boundary_surface_attribute{}.uro_ifc_pset_site_common_uro_buildable_area_units xml_buffer, uro_ifc_boundary_surface_attribute{}.uro_ifc_pset_site_common_uro_total_area xml_real64, uro_ifc_boundary_surface_attribute{}.uro_ifc_pset_site_common_uro_total_area_units xml_buffer, uro_ifc_boundary_surface_attribute{}.uro_ifc_pset_site_common_uro_building_height_limit xml_real64, uro_ifc_boundary_surface_attribute{}.uro_ifc_pset_site_common_uro_building_height_limit_units xml_buffer, uro_ifc_boundary_surface_attribute{}.uro_ifc_pset_space_common_uro_reference xml_buffer, uro_ifc_boundary_surface_attribute{}.uro_ifc_pset_space_common_uro_category xml_buffer, uro_ifc_boundary_surface_attribute{}.uro_ifc_pset_space_common_uro_category_codeSpace xml_buffer, uro_ifc_boundary_surface_attribute{}.uro_ifc_pset_space_common_uro_floor_covering xml_buffer, uro_ifc_boundary_surface_attribute{}.uro_ifc_pset_space_common_uro_wall_covering xml_buffer, uro_ifc_boundary_surface_attribute{}.uro_ifc_pset_space_common_uro_ceiling_covering xml_buffer, uro_ifc_boundary_surface_attribute{}.uro_ifc_pset_space_common_uro_skirting_covering xml_buffer, uro_ifc_boundary_surface_attribute{}.uro_ifc_pset_space_common_uro_gross_planned_area xml_real64, uro_ifc_boundary_surface_attribute{}.uro_ifc_pset_space_common_uro_gross_planned_area_units xml_buffer, uro_ifc_boundary_surface_attribute{}.uro_ifc_pset_space_common_uro_net_planned_area xml_real64, uro_ifc_boundary_surface_attribute{}.uro_ifc_pset_space_common_uro_net_planned_area_units xml_buffer, uro_ifc_boundary_surface_attribute{}.uro_ifc_pset_space_common_uro_publicly_accessible xml_boolean, uro_ifc_boundary_surface_attribute{}.uro_ifc_pset_space_common_uro_handicap_accessible xml_boolean, uro_ifc_boundary_surface_attribute{}.uro_ifc_pset_space_common_uro_concealed_flooring xml_boolean, uro_ifc_boundary_surface_attribute{}.uro_ifc_pset_space_common_uro_concealed_ceiling xml_boolean, uro_ifc_boundary_surface_attribute{}.uro_ifc_pset_window_common_uro_reference xml_buffer, uro_ifc_boundary_surface_attribute{}.uro_ifc_pset_window_common_uro_acoustic_rating xml_buffer, uro_ifc_boundary_surface_attribute{}.uro_ifc_pset_window_common_uro_firerating xml_buffer, uro_ifc_boundary_surface_attribute{}.uro_ifc_pset_window_common_uro_security_rating xml_buffer, uro_ifc_boundary_surface_attribute{}.uro_ifc_pset_window_common_uro_is_external xml_boolean, uro_ifc_boundary_surface_attribute{}.uro_ifc_pset_window_common_uro_infiltration xml_real64, uro_ifc_boundary_surface_attribute{}.uro_ifc_pset_window_common_uro_thermal_transmittance xml_real64, uro_ifc_boundary_surface_attribute{}.uro_ifc_pset_window_common_uro_glazing_area_fraction xml_real64,
      uro_ifc_boundary_surface_attribute{}.uro_ifc_pset_window_common_uro_smoke_stop xml_boolean, uro_ifc_boundary_surface_attribute{}.uro_ifc_site_uro_global_id xml_buffer, uro_ifc_boundary_surface_attribute{}.uro_ifc_site_uro_name xml_buffer, uro_ifc_boundary_surface_attribute{}.uro_ifc_site_uro_description xml_buffer, uro_ifc_boundary_surface_attribute{}.uro_ifc_site_uro_object_type xml_buffer, uro_ifc_boundary_surface_attribute{}.uro_ifc_site_uro_long_name xml_buffer, uro_ifc_boundary_surface_attribute{}.uro_ifc_site_uro_composition_type xml_char(7), uro_ifc_boundary_surface_attribute{}.uro_ifc_site_uro_ref_longitude xml_real64, uro_ifc_boundary_surface_attribute{}.uro_ifc_site_uro_ref_latitude xml_real64, uro_ifc_boundary_surface_attribute{}.uro_ifc_site_uro_ref_elevation xml_real64, uro_ifc_boundary_surface_attribute{}.uro_ifc_site_uro_ref_elevation_units xml_buffer, uro_ifc_boundary_surface_attribute{}.uro_ifc_site_uro_land_title_number xml_buffer, uro_ifc_boundary_surface_attribute{}.uro_ifc_site_uro_site_address_xlink_href xml_buffer, uro_ifc_boundary_surface_attribute{}.uro_ifc_space_uro_global_id xml_buffer, uro_ifc_boundary_surface_attribute{}.uro_ifc_space_uro_name xml_buffer, uro_ifc_boundary_surface_attribute{}.uro_ifc_space_uro_description xml_buffer, uro_ifc_boundary_surface_attribute{}.uro_ifc_space_uro_object_type xml_buffer, uro_ifc_boundary_surface_attribute{}.uro_ifc_space_uro_long_name xml_buffer, uro_ifc_boundary_surface_attribute{}.uro_ifc_space_uro_composition_type xml_char(7), uro_ifc_boundary_surface_attribute{}.uro_ifc_space_uro_interioror_exterior_space xml_char(10), uro_ifc_boundary_surface_attribute{}.uro_ifc_space_uro_elevation_with_flooring xml_real64, uro_ifc_boundary_surface_attribute{}.uro_ifc_space_uro_elevation_with_flooring_units xml_buffer, uro_ifc_boundary_surface_attribute{}.uro_ifc_space_base_quantity_uro_nominal_height xml_real64, uro_ifc_boundary_surface_attribute{}.uro_ifc_space_base_quantity_uro_nominal_height_units xml_buffer, uro_ifc_boundary_surface_attribute{}.uro_ifc_space_base_quantity_uro_clear_height xml_real64, uro_ifc_boundary_surface_attribute{}.uro_ifc_space_base_quantity_uro_clear_height_units xml_buffer, uro_ifc_boundary_surface_attribute{}.uro_ifc_space_base_quantity_uro_finish_ceiling_height xml_real64, uro_ifc_boundary_surface_attribute{}.uro_ifc_space_base_quantity_uro_finish_ceiling_height_units xml_buffer, uro_ifc_boundary_surface_attribute{}.uro_ifc_space_base_quantity_uro_gross_perimeter xml_real64, uro_ifc_boundary_surface_attribute{}.uro_ifc_space_base_quantity_uro_gross_perimeter_units xml_buffer,
      uro_ifc_boundary_surface_attribute{}.uro_ifc_space_base_quantity_uro_net_perimeter xml_real64, uro_ifc_boundary_surface_attribute{}.uro_ifc_space_base_quantity_uro_net_perimeter_units xml_buffer, uro_ifc_boundary_surface_attribute{}.uro_ifc_space_base_quantity_uro_gross_ceiling_area xml_real64, uro_ifc_boundary_surface_attribute{}.uro_ifc_space_base_quantity_uro_gross_ceiling_area_units xml_buffer, uro_ifc_boundary_surface_attribute{}.uro_ifc_space_base_quantity_uro_gross_floor_area xml_real64, uro_ifc_boundary_surface_attribute{}.uro_ifc_space_base_quantity_uro_gross_floor_area_units xml_buffer, uro_ifc_boundary_surface_attribute{}.uro_ifc_space_base_quantity_uro_net_ceiling_area xml_real64, uro_ifc_boundary_surface_attribute{}.uro_ifc_space_base_quantity_uro_net_ceiling_area_units xml_buffer, uro_ifc_boundary_surface_attribute{}.uro_ifc_space_base_quantity_uro_net_floor_area xml_real64, uro_ifc_boundary_surface_attribute{}.uro_ifc_space_base_quantity_uro_net_floor_area_units xml_buffer, uro_ifc_boundary_surface_attribute{}.uro_ifc_space_base_quantity_uro_gross_wall_area xml_real64, uro_ifc_boundary_surface_attribute{}.uro_ifc_space_base_quantity_uro_gross_wall_area_units xml_buffer, uro_ifc_boundary_surface_attribute{}.uro_ifc_space_base_quantity_uro_net_wall_area xml_real64, uro_ifc_boundary_surface_attribute{}.uro_ifc_space_base_quantity_uro_net_wall_area_units xml_buffer, uro_ifc_boundary_surface_attribute{}.uro_ifc_space_base_quantity_uro_gross_volume xml_real64, uro_ifc_boundary_surface_attribute{}.uro_ifc_space_base_quantity_uro_gross_volume_units xml_buffer, uro_ifc_boundary_surface_attribute{}.uro_ifc_space_base_quantity_uro_net_volume xml_real64, uro_ifc_boundary_surface_attribute{}.uro_ifc_space_base_quantity_uro_net_volume_units xml_buffer, uro_ifc_boundary_surface_attribute{}.uro_ifc_wall_uro_global_id xml_buffer, uro_ifc_boundary_surface_attribute{}.uro_ifc_wall_uro_name xml_buffer, uro_ifc_boundary_surface_attribute{}.uro_ifc_wall_uro_description xml_buffer, uro_ifc_boundary_surface_attribute{}.uro_ifc_wall_uro_object_type xml_buffer, uro_ifc_boundary_surface_attribute{}.uro_ifc_wall_uro_tag xml_buffer, uro_ifc_boundary_surface_attribute{}.uro_ifc_wall_uro_element_type xml_buffer, uro_ifc_boundary_surface_attribute{}.uro_ifc_wall_uro_element_type_codeSpace xml_buffer, uro_ifc_boundary_surface_attribute{}.uro_ifc_wall_uro_predefined_type xml_buffer, uro_ifc_boundary_surface_attribute{}.uro_ifc_wall_uro_predefined_type_codeSpace xml_buffer, uro_ifc_boundary_surface_attribute{}.uro_ifc_wall_uro_shape_type xml_buffer, uro_ifc_boundary_surface_attribute{}.uro_ifc_wall_uro_shape_type_codeSpace xml_buffer, uro_ifc_boundary_surface_attribute{}.uro_ifc_wall_uro_number_of_riser xml_int64,
      uro_ifc_boundary_surface_attribute{}.uro_ifc_wall_uro_number_of_treads xml_int64, uro_ifc_boundary_surface_attribute{}.uro_ifc_wall_uro_riser_height xml_int64, uro_ifc_boundary_surface_attribute{}.uro_ifc_wall_uro_tread_length xml_int64, uro_ifc_boundary_surface_attribute{}.uro_ifc_wall_uro_operation_type xml_char(11), uro_ifc_boundary_surface_attribute{}.uro_ifc_wall_uro_capacity_by_weight xml_real64, uro_ifc_boundary_surface_attribute{}.uro_ifc_wall_uro_capacity_by_weight_units xml_buffer, uro_ifc_boundary_surface_attribute{}.uro_ifc_wall_uro_capacity_by_number xml_int64, uro_ifc_boundary_surface_attribute{}.uro_ifc_wall_uro_nominal_length xml_real64, uro_ifc_boundary_surface_attribute{}.uro_ifc_wall_uro_nominal_length_units xml_buffer, uro_ifc_boundary_surface_attribute{}.uro_ifc_wall_uro_nominal_width xml_real64, uro_ifc_boundary_surface_attribute{}.uro_ifc_wall_uro_nominal_width_units xml_buffer, uro_ifc_boundary_surface_attribute{}.uro_ifc_wall_uro_nominal_height xml_real64, uro_ifc_boundary_surface_attribute{}.uro_ifc_wall_uro_nominal_height_units xml_buffer, uro_ifc_boundary_surface_attribute{}.uro_ifc_wall_uro_gross_foot_print_area xml_real64, uro_ifc_boundary_surface_attribute{}.uro_ifc_wall_uro_gross_foot_print_area_units xml_buffer, uro_ifc_boundary_surface_attribute{}.uro_ifc_wall_uro_net_foot_print_area xml_real64, uro_ifc_boundary_surface_attribute{}.uro_ifc_wall_uro_net_foot_print_area_units xml_buffer, uro_ifc_boundary_surface_attribute{}.uro_ifc_wall_uro_gross_side_area xml_real64, uro_ifc_boundary_surface_attribute{}.uro_ifc_wall_uro_gross_side_area_units xml_buffer, uro_ifc_boundary_surface_attribute{}.uro_ifc_wall_uro_net_side_area xml_real64, uro_ifc_boundary_surface_attribute{}.uro_ifc_wall_uro_net_side_area_units xml_buffer, uro_ifc_boundary_surface_attribute{}.uro_ifc_wall_uro_gross_side_area_left xml_real64, uro_ifc_boundary_surface_attribute{}.uro_ifc_wall_uro_gross_side_area_left_units xml_buffer, uro_ifc_boundary_surface_attribute{}.uro_ifc_wall_uro_net_side_area_left xml_real64, uro_ifc_boundary_surface_attribute{}.uro_ifc_wall_uro_net_side_area_left_units xml_buffer, uro_ifc_boundary_surface_attribute{}.uro_ifc_wall_uro_gross_side_area_right xml_real64, uro_ifc_boundary_surface_attribute{}.uro_ifc_wall_uro_gross_side_area_right_units xml_buffer, uro_ifc_boundary_surface_attribute{}.uro_ifc_wall_uro_net_side_area_right xml_real64, uro_ifc_boundary_surface_attribute{}.uro_ifc_wall_uro_net_side_area_right_units xml_buffer, uro_ifc_boundary_surface_attribute{}.uro_ifc_wall_uro_gross_volume xml_real64,
      uro_ifc_boundary_surface_attribute{}.uro_ifc_wall_uro_gross_volume_units xml_buffer, uro_ifc_boundary_surface_attribute{}.uro_ifc_wall_uro_net_volume xml_real64, uro_ifc_boundary_surface_attribute{}.uro_ifc_wall_uro_net_volume_units xml_buffer, uro_ifc_boundary_surface_attribute{}.uro_ifc_wall_standard_case_uro_global_id xml_buffer, uro_ifc_boundary_surface_attribute{}.uro_ifc_wall_standard_case_uro_name xml_buffer, uro_ifc_boundary_surface_attribute{}.uro_ifc_wall_standard_case_uro_description xml_buffer, uro_ifc_boundary_surface_attribute{}.uro_ifc_wall_standard_case_uro_object_type xml_buffer, uro_ifc_boundary_surface_attribute{}.uro_ifc_wall_standard_case_uro_tag xml_buffer, uro_ifc_boundary_surface_attribute{}.uro_ifc_wall_standard_case_uro_element_type xml_buffer, uro_ifc_boundary_surface_attribute{}.uro_ifc_wall_standard_case_uro_element_type_codeSpace xml_buffer, uro_ifc_boundary_surface_attribute{}.uro_ifc_wall_standard_case_uro_predefined_type xml_buffer, uro_ifc_boundary_surface_attribute{}.uro_ifc_wall_standard_case_uro_predefined_type_codeSpace xml_buffer, uro_ifc_boundary_surface_attribute{}.uro_ifc_wall_standard_case_uro_shape_type xml_buffer, uro_ifc_boundary_surface_attribute{}.uro_ifc_wall_standard_case_uro_shape_type_codeSpace xml_buffer, uro_ifc_boundary_surface_attribute{}.uro_ifc_wall_standard_case_uro_number_of_riser xml_int64, uro_ifc_boundary_surface_attribute{}.uro_ifc_wall_standard_case_uro_number_of_treads xml_int64, uro_ifc_boundary_surface_attribute{}.uro_ifc_wall_standard_case_uro_riser_height xml_int64, uro_ifc_boundary_surface_attribute{}.uro_ifc_wall_standard_case_uro_tread_length xml_int64, uro_ifc_boundary_surface_attribute{}.uro_ifc_wall_standard_case_uro_operation_type xml_char(11), uro_ifc_boundary_surface_attribute{}.uro_ifc_wall_standard_case_uro_capacity_by_weight xml_real64, uro_ifc_boundary_surface_attribute{}.uro_ifc_wall_standard_case_uro_capacity_by_weight_units xml_buffer, uro_ifc_boundary_surface_attribute{}.uro_ifc_wall_standard_case_uro_capacity_by_number xml_int64, uro_ifc_boundary_surface_attribute{}.uro_ifc_wall_standard_case_uro_nominal_length xml_real64, uro_ifc_boundary_surface_attribute{}.uro_ifc_wall_standard_case_uro_nominal_length_units xml_buffer, uro_ifc_boundary_surface_attribute{}.uro_ifc_wall_standard_case_uro_nominal_width xml_real64, uro_ifc_boundary_surface_attribute{}.uro_ifc_wall_standard_case_uro_nominal_width_units xml_buffer, uro_ifc_boundary_surface_attribute{}.uro_ifc_wall_standard_case_uro_nominal_height xml_real64, uro_ifc_boundary_surface_attribute{}.uro_ifc_wall_standard_case_uro_nominal_height_units xml_buffer, uro_ifc_boundary_surface_attribute{}.uro_ifc_wall_standard_case_uro_gross_foot_print_area xml_real64, uro_ifc_boundary_surface_attribute{}.uro_ifc_wall_standard_case_uro_gross_foot_print_area_units xml_buffer,
      uro_ifc_boundary_surface_attribute{}.uro_ifc_wall_standard_case_uro_net_foot_print_area xml_real64, uro_ifc_boundary_surface_attribute{}.uro_ifc_wall_standard_case_uro_net_foot_print_area_units xml_buffer, uro_ifc_boundary_surface_attribute{}.uro_ifc_wall_standard_case_uro_gross_side_area xml_real64, uro_ifc_boundary_surface_attribute{}.uro_ifc_wall_standard_case_uro_gross_side_area_units xml_buffer, uro_ifc_boundary_surface_attribute{}.uro_ifc_wall_standard_case_uro_net_side_area xml_real64, uro_ifc_boundary_surface_attribute{}.uro_ifc_wall_standard_case_uro_net_side_area_units xml_buffer, uro_ifc_boundary_surface_attribute{}.uro_ifc_wall_standard_case_uro_gross_side_area_left xml_real64, uro_ifc_boundary_surface_attribute{}.uro_ifc_wall_standard_case_uro_gross_side_area_left_units xml_buffer, uro_ifc_boundary_surface_attribute{}.uro_ifc_wall_standard_case_uro_net_side_area_left xml_real64, uro_ifc_boundary_surface_attribute{}.uro_ifc_wall_standard_case_uro_net_side_area_left_units xml_buffer, uro_ifc_boundary_surface_attribute{}.uro_ifc_wall_standard_case_uro_gross_side_area_right xml_real64, uro_ifc_boundary_surface_attribute{}.uro_ifc_wall_standard_case_uro_gross_side_area_right_units xml_buffer, uro_ifc_boundary_surface_attribute{}.uro_ifc_wall_standard_case_uro_net_side_area_right xml_real64, uro_ifc_boundary_surface_attribute{}.uro_ifc_wall_standard_case_uro_net_side_area_right_units xml_buffer, uro_ifc_boundary_surface_attribute{}.uro_ifc_wall_standard_case_uro_gross_volume xml_real64, uro_ifc_boundary_surface_attribute{}.uro_ifc_wall_standard_case_uro_gross_volume_units xml_buffer, uro_ifc_boundary_surface_attribute{}.uro_ifc_wall_standard_case_uro_net_volume xml_real64, uro_ifc_boundary_surface_attribute{}.uro_ifc_wall_standard_case_uro_net_volume_units xml_buffer, uro_ifc_boundary_surface_attribute{}.uro_ifc_window_uro_global_id xml_buffer, uro_ifc_boundary_surface_attribute{}.uro_ifc_window_uro_name xml_buffer, uro_ifc_boundary_surface_attribute{}.uro_ifc_window_uro_description xml_buffer, uro_ifc_boundary_surface_attribute{}.uro_ifc_window_uro_object_type xml_buffer, uro_ifc_boundary_surface_attribute{}.uro_ifc_window_uro_tag xml_buffer, uro_ifc_boundary_surface_attribute{}.uro_ifc_window_uro_element_type xml_buffer, uro_ifc_boundary_surface_attribute{}.uro_ifc_window_uro_element_type_codeSpace xml_buffer, uro_ifc_boundary_surface_attribute{}.uro_ifc_window_uro_predefined_type xml_buffer, uro_ifc_boundary_surface_attribute{}.uro_ifc_window_uro_predefined_type_codeSpace xml_buffer, uro_ifc_boundary_surface_attribute{}.uro_ifc_window_uro_shape_type xml_buffer, uro_ifc_boundary_surface_attribute{}.uro_ifc_window_uro_shape_type_codeSpace xml_buffer, uro_ifc_boundary_surface_attribute{}.uro_ifc_window_uro_number_of_riser xml_int64,
      uro_ifc_boundary_surface_attribute{}.uro_ifc_window_uro_number_of_treads xml_int64, uro_ifc_boundary_surface_attribute{}.uro_ifc_window_uro_riser_height xml_int64, uro_ifc_boundary_surface_attribute{}.uro_ifc_window_uro_tread_length xml_int64, uro_ifc_boundary_surface_attribute{}.uro_ifc_window_uro_operation_type xml_char(11), uro_ifc_boundary_surface_attribute{}.uro_ifc_window_uro_capacity_by_weight xml_real64, uro_ifc_boundary_surface_attribute{}.uro_ifc_window_uro_capacity_by_weight_units xml_buffer, uro_ifc_boundary_surface_attribute{}.uro_ifc_window_uro_capacity_by_number xml_int64, uro_ifc_boundary_surface_attribute{}.uro_ifc_window_uro_overall_height xml_real64, uro_ifc_boundary_surface_attribute{}.uro_ifc_window_uro_overall_height_units xml_buffer, uro_ifc_boundary_surface_attribute{}.uro_ifc_window_uro_overall_width xml_real64, uro_ifc_boundary_surface_attribute{}.uro_ifc_window_uro_overall_width_units xml_buffer
Note: 2DForcer : Input
Junction_81
    -> Junction_82
Note: AttributeCreator_7 : Output / FllorSurface
Junction_82
    -> 2DForcer
2DForcer
    2D -> DonutHoleExtractor
DonutHoleExtractor
    DEAGGREGATE_INPUT = Yes
    OUTERSHELL -> SpatialFilter_4 [Filter]
SpatialFilter_4
    AGGREGATE_HANDLING = Yes
    BASE_TYPE = Multiple Filters
    CURVE_BOUNDARY_RULE_PARAM = Default Rule
    GROUP_BY = _building_id _storey_id
    PASS_CRITERIA = Pass Against One Filter
    PREDATTR = _predicate
    PREDICATES = CONTAINS
    USE_BOUNDING_BOX = No
    PASSED -> GeometryReplacer_4
Note: AttributeManager_13 : Input / Room ソリッドに集約
Junction_21
    -> Junction_26
Note: FloorSurface / AttributeManager_6 : Output
Junction_26
    -> AttributeManager_13
Note: 屋内壁: InteriorWallSurface
AttributeManager_7
    ATTR_TABLE:
      SET_TO gml_id = iwall_@UUID()
      SET_TO _citygml_feature_type = InteriorWallSurface
      REMOVE _surfaceNormalX
      REMOVE _surfaceNormalY
      REMOVE _surfaceNormalZ
      REMOVE _pointOnSurfaceX
      REMOVE _pointOnSurfaceY
      REMOVE _pointOnSurfaceZ
      REMOVE _clipped
      SET_TO citygml_lod_name = lod4MultiSurface
      SET_TO citygml_feature_role = boundedBy
    -> GeometryPropertySetter_6
    -> Junction_70
GeometryPropertySetter_6
    GQUERY:
      for $geom in //geometry
      where $geom/count(parent::geometry) = 0
      return number($geom/@fme_id)
    OVERWRITE_CHOICE = Yes
    REMOVE_ATTRIBUTE = Yes
    SETTYPE_PARAM = Traits From Attributes
    SRC_ATTRS = citygml_lod_name gml_id
    SET -> AttributeCreator_4
AttributeCreator_4
    ATTR_TABLE:
      SET_TO gml_id = @Value(_boundary_gml_id)
      SET_TO gml_parent_id = @Value(_room_gml_id)
    -> PLATEAU.IfcReprojector_9 [IfcFeature]
PLATEAU.IfcReprojector_9
    DEST_COORDSYS = $(DEST_COORDSYS)
    LENGTH_MULTIPLIER = @Value(_lengthmultiplier)
    REPROJECTION_PARAMS = @Value(_reprojection_params)
    Reprojected -> InteriorWallSurface (writer CITYGML_2)
InteriorWallSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, uro_ifc_boundary_surface_attribute{}.uro_ifc_building_uro_global_id xml_buffer, uro_ifc_boundary_surface_attribute{}.uro_ifc_building_uro_name xml_buffer, uro_ifc_boundary_surface_attribute{}.uro_ifc_building_uro_description xml_buffer, uro_ifc_boundary_surface_attribute{}.uro_ifc_building_uro_object_type xml_buffer, uro_ifc_boundary_surface_attribute{}.uro_ifc_building_uro_long_name xml_buffer, uro_ifc_boundary_surface_attribute{}.uro_ifc_building_uro_composition_type xml_char(7), uro_ifc_boundary_surface_attribute{}.uro_ifc_building_uro_elevation_of_ref_height xml_real64, uro_ifc_boundary_surface_attribute{}.uro_ifc_building_uro_elevation_of_ref_height_units xml_buffer, uro_ifc_boundary_surface_attribute{}.uro_ifc_building_uro_elevation_of_terrain xml_real64, uro_ifc_boundary_surface_attribute{}.uro_ifc_building_uro_elevation_of_terrain_units xml_buffer, uro_ifc_boundary_surface_attribute{}.uro_ifc_building_uro_building_address_xlink_href xml_buffer, uro_ifc_boundary_surface_attribute{}.uro_ifc_building_element_uro_global_id xml_buffer, uro_ifc_boundary_surface_attribute{}.uro_ifc_building_element_uro_name xml_buffer, uro_ifc_boundary_surface_attribute{}.uro_ifc_building_element_uro_description xml_buffer,
      uro_ifc_boundary_surface_attribute{}.uro_ifc_building_element_uro_object_type xml_buffer, uro_ifc_boundary_surface_attribute{}.uro_ifc_building_element_uro_tag xml_buffer, uro_ifc_boundary_surface_attribute{}.uro_ifc_building_element_uro_element_type xml_buffer, uro_ifc_boundary_surface_attribute{}.uro_ifc_building_element_uro_element_type_codeSpace xml_buffer, uro_ifc_boundary_surface_attribute{}.uro_ifc_building_element_uro_predefined_type xml_buffer, uro_ifc_boundary_surface_attribute{}.uro_ifc_building_element_uro_predefined_type_codeSpace xml_buffer, uro_ifc_boundary_surface_attribute{}.uro_ifc_building_element_uro_shape_type xml_buffer, uro_ifc_boundary_surface_attribute{}.uro_ifc_building_element_uro_shape_type_codeSpace xml_buffer, uro_ifc_boundary_surface_attribute{}.uro_ifc_building_element_uro_number_of_riser xml_int64, uro_ifc_boundary_surface_attribute{}.uro_ifc_building_element_uro_number_of_treads xml_int64, uro_ifc_boundary_surface_attribute{}.uro_ifc_building_element_uro_riser_height xml_int64, uro_ifc_boundary_surface_attribute{}.uro_ifc_building_element_uro_tread_length xml_int64, uro_ifc_boundary_surface_attribute{}.uro_ifc_building_element_uro_operation_type xml_char(11), uro_ifc_boundary_surface_attribute{}.uro_ifc_building_element_uro_capacity_by_weight xml_real64, uro_ifc_boundary_surface_attribute{}.uro_ifc_building_element_uro_capacity_by_weight_units xml_buffer, uro_ifc_boundary_surface_attribute{}.uro_ifc_building_element_uro_capacity_by_number xml_int64, uro_ifc_boundary_surface_attribute{}.uro_ifc_building_storey_uro_global_id xml_buffer, uro_ifc_boundary_surface_attribute{}.uro_ifc_building_storey_uro_name xml_buffer, uro_ifc_boundary_surface_attribute{}.uro_ifc_building_storey_uro_description xml_buffer, uro_ifc_boundary_surface_attribute{}.uro_ifc_building_storey_uro_object_type xml_buffer, uro_ifc_boundary_surface_attribute{}.uro_ifc_building_storey_uro_long_name xml_buffer, uro_ifc_boundary_surface_attribute{}.uro_ifc_building_storey_uro_composition_type xml_char(7), uro_ifc_boundary_surface_attribute{}.uro_ifc_building_storey_uro_elevation xml_real64, uro_ifc_boundary_surface_attribute{}.uro_ifc_building_storey_uro_elevation_units xml_buffer, uro_ifc_boundary_surface_attribute{}.uro_ifc_classification_reference_uro_location xml_buffer, uro_ifc_boundary_surface_attribute{}.uro_ifc_classification_reference_uro_item_reference xml_buffer, uro_ifc_boundary_surface_attribute{}.uro_ifc_classification_reference_uro_item_reference_codeSpace xml_buffer, uro_ifc_boundary_surface_attribute{}.uro_ifc_classification_reference_uro_name xml_buffer, uro_ifc_boundary_surface_attribute{}.uro_ifc_classification_reference_uro_name_codeSpace xml_buffer, uro_ifc_boundary_surface_attribute{}.uro_ifc_classification_reference_uro_reference_source_uro_ifc_classification_uro_source xml_buffer,
      uro_ifc_boundary_surface_attribute{}.uro_ifc_classification_reference_uro_reference_source_uro_ifc_classification_uro_edition xml_buffer, uro_ifc_boundary_surface_attribute{}.uro_ifc_classification_reference_uro_reference_source_uro_ifc_classification_uro_edition_date xml_date, uro_ifc_boundary_surface_attribute{}.uro_ifc_classification_reference_uro_reference_source_uro_ifc_classification_uro_name xml_buffer, uro_ifc_boundary_surface_attribute{}.uro_ifc_coordinate_reference_system_uro_name xml_buffer, uro_ifc_boundary_surface_attribute{}.uro_ifc_coordinate_reference_system_uro_description xml_buffer, uro_ifc_boundary_surface_attribute{}.uro_ifc_coordinate_reference_system_uro_geodetic_datum xml_buffer, uro_ifc_boundary_surface_attribute{}.uro_ifc_coordinate_reference_system_uro_vertical_datum xml_buffer, uro_ifc_boundary_surface_attribute{}.uro_ifc_curtain_wall_uro_global_id xml_buffer, uro_ifc_boundary_surface_attribute{}.uro_ifc_curtain_wall_uro_name xml_buffer, uro_ifc_boundary_surface_attribute{}.uro_ifc_curtain_wall_uro_description xml_buffer, uro_ifc_boundary_surface_attribute{}.uro_ifc_curtain_wall_uro_object_type xml_buffer, uro_ifc_boundary_surface_attribute{}.uro_ifc_curtain_wall_uro_tag xml_buffer, uro_ifc_boundary_surface_attribute{}.uro_ifc_curtain_wall_uro_element_type xml_buffer, uro_ifc_boundary_surface_attribute{}.uro_ifc_curtain_wall_uro_element_type_codeSpace xml_buffer, uro_ifc_boundary_surface_attribute{}.uro_ifc_curtain_wall_uro_predefined_type xml_buffer, uro_ifc_boundary_surface_attribute{}.uro_ifc_curtain_wall_uro_predefined_type_codeSpace xml_buffer, uro_ifc_boundary_surface_attribute{}.uro_ifc_curtain_wall_uro_shape_type xml_buffer, uro_ifc_boundary_surface_attribute{}.uro_ifc_curtain_wall_uro_shape_type_codeSpace xml_buffer, uro_ifc_boundary_surface_attribute{}.uro_ifc_curtain_wall_uro_number_of_riser xml_int64, uro_ifc_boundary_surface_attribute{}.uro_ifc_curtain_wall_uro_number_of_treads xml_int64, uro_ifc_boundary_surface_attribute{}.uro_ifc_curtain_wall_uro_riser_height xml_int64, uro_ifc_boundary_surface_attribute{}.uro_ifc_curtain_wall_uro_tread_length xml_int64, uro_ifc_boundary_surface_attribute{}.uro_ifc_curtain_wall_uro_operation_type xml_char(11), uro_ifc_boundary_surface_attribute{}.uro_ifc_curtain_wall_uro_capacity_by_weight xml_real64, uro_ifc_boundary_surface_attribute{}.uro_ifc_curtain_wall_uro_capacity_by_weight_units xml_buffer, uro_ifc_boundary_surface_attribute{}.uro_ifc_curtain_wall_uro_capacity_by_number xml_int64, uro_ifc_boundary_surface_attribute{}.uro_ifc_door_uro_global_id xml_buffer, uro_ifc_boundary_surface_attribute{}.uro_ifc_door_uro_name xml_buffer, uro_ifc_boundary_surface_attribute{}.uro_ifc_door_uro_description xml_buffer, uro_ifc_boundary_surface_attribute{}.uro_ifc_door_uro_object_type xml_buffer,
      uro_ifc_boundary_surface_attribute{}.uro_ifc_door_uro_tag xml_buffer, uro_ifc_boundary_surface_attribute{}.uro_ifc_door_uro_element_type xml_buffer, uro_ifc_boundary_surface_attribute{}.uro_ifc_door_uro_element_type_codeSpace xml_buffer, uro_ifc_boundary_surface_attribute{}.uro_ifc_door_uro_predefined_type xml_buffer, uro_ifc_boundary_surface_attribute{}.uro_ifc_door_uro_predefined_type_codeSpace xml_buffer, uro_ifc_boundary_surface_attribute{}.uro_ifc_door_uro_shape_type xml_buffer, uro_ifc_boundary_surface_attribute{}.uro_ifc_door_uro_shape_type_codeSpace xml_buffer, uro_ifc_boundary_surface_attribute{}.uro_ifc_door_uro_number_of_riser xml_int64, uro_ifc_boundary_surface_attribute{}.uro_ifc_door_uro_number_of_treads xml_int64, uro_ifc_boundary_surface_attribute{}.uro_ifc_door_uro_riser_height xml_int64, uro_ifc_boundary_surface_attribute{}.uro_ifc_door_uro_tread_length xml_int64, uro_ifc_boundary_surface_attribute{}.uro_ifc_door_uro_operation_type xml_char(11), uro_ifc_boundary_surface_attribute{}.uro_ifc_door_uro_capacity_by_weight xml_real64, uro_ifc_boundary_surface_attribute{}.uro_ifc_door_uro_capacity_by_weight_units xml_buffer, uro_ifc_boundary_surface_attribute{}.uro_ifc_door_uro_capacity_by_number xml_int64, uro_ifc_boundary_surface_attribute{}.uro_ifc_door_uro_overall_height xml_real64, uro_ifc_boundary_surface_attribute{}.uro_ifc_door_uro_overall_height_units xml_buffer, uro_ifc_boundary_surface_attribute{}.uro_ifc_door_uro_overall_width xml_real64, uro_ifc_boundary_surface_attribute{}.uro_ifc_door_uro_overall_width_units xml_buffer, uro_ifc_boundary_surface_attribute{}.uro_ifc_furnishing_element_uro_global_id xml_buffer, uro_ifc_boundary_surface_attribute{}.uro_ifc_furnishing_element_uro_name xml_buffer, uro_ifc_boundary_surface_attribute{}.uro_ifc_furnishing_element_uro_description xml_buffer, uro_ifc_boundary_surface_attribute{}.uro_ifc_furnishing_element_uro_object_type xml_buffer, uro_ifc_boundary_surface_attribute{}.uro_ifc_furnishing_element_uro_tag xml_buffer, uro_ifc_boundary_surface_attribute{}.uro_ifc_map_conversion_uro_source_crs_uro_crs_uro_ifc_projected_crs_uro_name xml_buffer, uro_ifc_boundary_surface_attribute{}.uro_ifc_map_conversion_uro_source_crs_uro_crs_uro_ifc_projected_crs_uro_description xml_buffer, uro_ifc_boundary_surface_attribute{}.uro_ifc_map_conversion_uro_source_crs_uro_crs_uro_ifc_projected_crs_uro_geodetic_datum xml_buffer, uro_ifc_boundary_surface_attribute{}.uro_ifc_map_conversion_uro_source_crs_uro_crs_uro_ifc_projected_crs_uro_vertical_datum xml_buffer, uro_ifc_boundary_surface_attribute{}.uro_ifc_map_conversion_uro_source_crs_uro_crs_uro_ifc_projected_crs_uro_map_unit xml_buffer, uro_ifc_boundary_surface_attribute{}.uro_ifc_map_conversion_uro_source_crs_uro_crs_uro_ifc_projected_crs_uro_map_projection xml_buffer,
      uro_ifc_boundary_surface_attribute{}.uro_ifc_map_conversion_uro_source_crs_uro_crs_uro_ifc_projected_crs_uro_map_zone xml_buffer, uro_ifc_boundary_surface_attribute{}.uro_ifc_map_conversion_uro_source_crs_uro_crs_uro_ifc_coordinate_reference_system_uro_name xml_buffer, uro_ifc_boundary_surface_attribute{}.uro_ifc_map_conversion_uro_source_crs_uro_crs_uro_ifc_coordinate_reference_system_uro_description xml_buffer, uro_ifc_boundary_surface_attribute{}.uro_ifc_map_conversion_uro_source_crs_uro_crs_uro_ifc_coordinate_reference_system_uro_geodetic_datum xml_buffer, uro_ifc_boundary_surface_attribute{}.uro_ifc_map_conversion_uro_source_crs_uro_crs_uro_ifc_coordinate_reference_system_uro_vertical_datum xml_buffer, uro_ifc_boundary_surface_attribute{}.uro_ifc_map_conversion_uro_source_crs_uro_context_uro_ifc_geometric_representation_context_uro_context_identifier xml_buffer, uro_ifc_boundary_surface_attribute{}.uro_ifc_map_conversion_uro_source_crs_uro_context_uro_ifc_geometric_representation_context_uro_context_type xml_buffer, uro_ifc_boundary_surface_attribute{}.uro_ifc_map_conversion_uro_source_crs_uro_context_uro_ifc_geometric_representation_context_uro_coordinate_space_dimension xml_int64, uro_ifc_boundary_surface_attribute{}.uro_ifc_map_conversion_uro_source_crs_uro_context_uro_ifc_geometric_representation_context_uro_precision xml_real64, uro_ifc_boundary_surface_attribute{}.uro_ifc_map_conversion_uro_source_crs_uro_context_uro_ifc_geometric_representation_context_uro_true_north xml_real64, uro_ifc_boundary_surface_attribute{}.uro_ifc_map_conversion_uro_target_crs_uro_ifc_projected_crs_uro_name xml_buffer, uro_ifc_boundary_surface_attribute{}.uro_ifc_map_conversion_uro_target_crs_uro_ifc_projected_crs_uro_description xml_buffer, uro_ifc_boundary_surface_attribute{}.uro_ifc_map_conversion_uro_target_crs_uro_ifc_projected_crs_uro_geodetic_datum xml_buffer, uro_ifc_boundary_surface_attribute{}.uro_ifc_map_conversion_uro_target_crs_uro_ifc_projected_crs_uro_vertical_datum xml_buffer, uro_ifc_boundary_surface_attribute{}.uro_ifc_map_conversion_uro_target_crs_uro_ifc_projected_crs_uro_map_unit xml_buffer, uro_ifc_boundary_surface_attribute{}.uro_ifc_map_conversion_uro_target_crs_uro_ifc_projected_crs_uro_map_projection xml_buffer, uro_ifc_boundary_surface_attribute{}.uro_ifc_map_conversion_uro_target_crs_uro_ifc_projected_crs_uro_map_zone xml_buffer, uro_ifc_boundary_surface_attribute{}.uro_ifc_map_conversion_uro_target_crs_uro_ifc_coordinate_reference_system_uro_name xml_buffer, uro_ifc_boundary_surface_attribute{}.uro_ifc_map_conversion_uro_target_crs_uro_ifc_coordinate_reference_system_uro_description xml_buffer, uro_ifc_boundary_surface_attribute{}.uro_ifc_map_conversion_uro_target_crs_uro_ifc_coordinate_reference_system_uro_geodetic_datum xml_buffer, uro_ifc_boundary_surface_attribute{}.uro_ifc_map_conversion_uro_target_crs_uro_ifc_coordinate_reference_system_uro_vertical_datum xml_buffer, uro_ifc_boundary_surface_attribute{}.uro_ifc_map_conversion_uro_eastings xml_buffer, uro_ifc_boundary_surface_attribute{}.uro_ifc_map_conversion_uro_northings xml_buffer, uro_ifc_boundary_surface_attribute{}.uro_ifc_map_conversion_uro_orthogonal_height xml_real64, uro_ifc_boundary_surface_attribute{}.uro_ifc_map_conversion_uro_orthogonal_height_units xml_buffer, uro_ifc_boundary_surface_attribute{}.uro_ifc_map_conversion_uro_x_axis_abscissa xml_real64, uro_ifc_boundary_surface_attribute{}.uro_ifc_map_conversion_uro_x_axis_ordinate xml_real64, uro_ifc_boundary_surface_attribute{}.uro_ifc_map_conversion_uro_scale xml_real64, uro_ifc_boundary_surface_attribute{}.uro_ifc_opening_element_uro_global_id xml_buffer, uro_ifc_boundary_surface_attribute{}.uro_ifc_opening_element_uro_name xml_buffer,
      uro_ifc_boundary_surface_attribute{}.uro_ifc_opening_element_uro_description xml_buffer, uro_ifc_boundary_surface_attribute{}.uro_ifc_opening_element_uro_object_type xml_buffer, uro_ifc_boundary_surface_attribute{}.uro_ifc_opening_element_uro_tag xml_buffer, uro_ifc_boundary_surface_attribute{}.uro_ifc_opening_element_uro_nominal_area xml_real64, uro_ifc_boundary_surface_attribute{}.uro_ifc_opening_element_uro_nominal_area_units xml_buffer, uro_ifc_boundary_surface_attribute{}.uro_ifc_opening_element_uro_nominal_volume xml_real64, uro_ifc_boundary_surface_attribute{}.uro_ifc_opening_element_uro_nominal_volume_units xml_buffer, uro_ifc_boundary_surface_attribute{}.uro_ifc_project_uro_global_id xml_buffer, uro_ifc_boundary_surface_attribute{}.uro_ifc_project_uro_name xml_buffer, uro_ifc_boundary_surface_attribute{}.uro_ifc_project_uro_description xml_buffer, uro_ifc_boundary_surface_attribute{}.uro_ifc_project_uro_object_type xml_buffer, uro_ifc_boundary_surface_attribute{}.uro_ifc_project_uro_long_name xml_buffer, uro_ifc_boundary_surface_attribute{}.uro_ifc_project_uro_phase xml_buffer, uro_ifc_boundary_surface_attribute{}.uro_ifc_project_uro_representation_contexts_uro_ifc_geometric_representation_context_uro_context_identifier xml_buffer, uro_ifc_boundary_surface_attribute{}.uro_ifc_project_uro_representation_contexts_uro_ifc_geometric_representation_context_uro_context_type xml_buffer, uro_ifc_boundary_surface_attribute{}.uro_ifc_project_uro_representation_contexts_uro_ifc_geometric_representation_context_uro_coordinate_space_dimension xml_int64, uro_ifc_boundary_surface_attribute{}.uro_ifc_project_uro_representation_contexts_uro_ifc_geometric_representation_context_uro_precision xml_real64, uro_ifc_boundary_surface_attribute{}.uro_ifc_project_uro_representation_contexts_uro_ifc_geometric_representation_context_uro_true_north xml_real64, uro_ifc_boundary_surface_attribute{}.uro_ifc_project_uro_units_in_context{}.uro_ifc_unit_uro_dimensions xml_int64, uro_ifc_boundary_surface_attribute{}.uro_ifc_project_uro_units_in_context{}.uro_ifc_unit_uro_unit_type xml_char(28), uro_ifc_boundary_surface_attribute{}.uro_ifc_project_uro_units_in_context{}.uro_ifc_unit_uro_perfix xml_buffer, uro_ifc_boundary_surface_attribute{}.uro_ifc_project_uro_units_in_context{}.uro_ifc_unit_uro_name xml_buffer, uro_ifc_boundary_surface_attribute{}.uro_ifc_projected_crs_uro_name xml_buffer, uro_ifc_boundary_surface_attribute{}.uro_ifc_projected_crs_uro_description xml_buffer, uro_ifc_boundary_surface_attribute{}.uro_ifc_projected_crs_uro_geodetic_datum xml_buffer, uro_ifc_boundary_surface_attribute{}.uro_ifc_projected_crs_uro_vertical_datum xml_buffer, uro_ifc_boundary_surface_attribute{}.uro_ifc_projected_crs_uro_map_unit xml_buffer, uro_ifc_boundary_surface_attribute{}.uro_ifc_projected_crs_uro_map_projection xml_buffer, uro_ifc_boundary_surface_attribute{}.uro_ifc_projected_crs_uro_map_zone xml_buffer, uro_ifc_boundary_surface_attribute{}.uro_ifc_pset_building_common_uro_building_id xml_real64,
      uro_ifc_boundary_surface_attribute{}.uro_ifc_pset_building_common_uro_building_id_units xml_buffer, uro_ifc_boundary_surface_attribute{}.uro_ifc_pset_building_common_uro_is_permanent_id xml_real64, uro_ifc_boundary_surface_attribute{}.uro_ifc_pset_building_common_uro_is_permanent_id_units xml_buffer, uro_ifc_boundary_surface_attribute{}.uro_ifc_pset_building_common_uro_main_fire_use xml_buffer, uro_ifc_boundary_surface_attribute{}.uro_ifc_pset_building_common_uro_ancillary_fire_use xml_buffer, uro_ifc_boundary_surface_attribute{}.uro_ifc_pset_building_common_uro_sprinkler_protection xml_boolean, uro_ifc_boundary_surface_attribute{}.uro_ifc_pset_building_common_uro_sprinkler_protection_automatic xml_boolean, uro_ifc_boundary_surface_attribute{}.uro_ifc_pset_building_common_uro_occupancy_type xml_buffer, uro_ifc_boundary_surface_attribute{}.uro_ifc_pset_building_common_uro_occupancy_type_codeSpace xml_buffer, uro_ifc_boundary_surface_attribute{}.uro_ifc_pset_building_common_uro_gross_planned_area xml_real64, uro_ifc_boundary_surface_attribute{}.uro_ifc_pset_building_common_uro_gross_planned_area_units xml_buffer, uro_ifc_boundary_surface_attribute{}.uro_ifc_pset_building_common_uro_number_of_storeys xml_int64, uro_ifc_boundary_surface_attribute{}.uro_ifc_pset_building_common_uro_year_of_construction xml_buffer, uro_ifc_boundary_surface_attribute{}.uro_ifc_pset_building_common_uro_is_landmarked xml_boolean, uro_ifc_boundary_surface_attribute{}.uro_ifc_pset_door_common_uro_reference xml_buffer, uro_ifc_boundary_surface_attribute{}.uro_ifc_pset_door_common_uro_acoustic_rating xml_buffer, uro_ifc_boundary_surface_attribute{}.uro_ifc_pset_door_common_uro_firerating xml_buffer, uro_ifc_boundary_surface_attribute{}.uro_ifc_pset_door_common_uro_security_rating xml_buffer, uro_ifc_boundary_surface_attribute{}.uro_ifc_pset_door_common_uro_is_external xml_boolean, uro_ifc_boundary_surface_attribute{}.uro_ifc_pset_door_common_uro_infiltration xml_real64, uro_ifc_boundary_surface_attribute{}.uro_ifc_pset_door_common_uro_thermal_transmittance xml_real64, uro_ifc_boundary_surface_attribute{}.uro_ifc_pset_door_common_uro_glazing_area_fraction xml_real64, uro_ifc_boundary_surface_attribute{}.uro_ifc_pset_door_common_uro_handicap_accessible xml_real64, uro_ifc_boundary_surface_attribute{}.uro_ifc_pset_door_common_uro_fire_exit xml_boolean, uro_ifc_boundary_surface_attribute{}.uro_ifc_pset_door_common_uro_self_closing xml_real64, uro_ifc_boundary_surface_attribute{}.uro_ifc_pset_door_common_uro_smoke_stop xml_boolean, uro_ifc_boundary_surface_attribute{}.uro_ifc_pset_opening_element_common_uro_reference xml_buffer, uro_ifc_boundary_surface_attribute{}.uro_ifc_pset_opening_element_common_uro_purpose xml_buffer, uro_ifc_boundary_surface_attribute{}.uro_ifc_pset_opening_element_common_uro_fire_exit xml_boolean, uro_ifc_boundary_surface_attribute{}.uro_ifc_pset_opening_element_common_uro_protected_opening xml_boolean,
      uro_ifc_boundary_surface_attribute{}.uro_ifc_pset_opening_element_common_uro_parallel_jambs xml_boolean, uro_ifc_boundary_surface_attribute{}.uro_ifc_pset_site_common_uro_buildable_area xml_real64, uro_ifc_boundary_surface_attribute{}.uro_ifc_pset_site_common_uro_buildable_area_units xml_buffer, uro_ifc_boundary_surface_attribute{}.uro_ifc_pset_site_common_uro_total_area xml_real64, uro_ifc_boundary_surface_attribute{}.uro_ifc_pset_site_common_uro_total_area_units xml_buffer, uro_ifc_boundary_surface_attribute{}.uro_ifc_pset_site_common_uro_building_height_limit xml_real64, uro_ifc_boundary_surface_attribute{}.uro_ifc_pset_site_common_uro_building_height_limit_units xml_buffer, uro_ifc_boundary_surface_attribute{}.uro_ifc_pset_space_common_uro_reference xml_buffer, uro_ifc_boundary_surface_attribute{}.uro_ifc_pset_space_common_uro_category xml_buffer, uro_ifc_boundary_surface_attribute{}.uro_ifc_pset_space_common_uro_category_codeSpace xml_buffer, uro_ifc_boundary_surface_attribute{}.uro_ifc_pset_space_common_uro_floor_covering xml_buffer, uro_ifc_boundary_surface_attribute{}.uro_ifc_pset_space_common_uro_wall_covering xml_buffer, uro_ifc_boundary_surface_attribute{}.uro_ifc_pset_space_common_uro_ceiling_covering xml_buffer, uro_ifc_boundary_surface_attribute{}.uro_ifc_pset_space_common_uro_skirting_covering xml_buffer, uro_ifc_boundary_surface_attribute{}.uro_ifc_pset_space_common_uro_gross_planned_area xml_real64, uro_ifc_boundary_surface_attribute{}.uro_ifc_pset_space_common_uro_gross_planned_area_units xml_buffer, uro_ifc_boundary_surface_attribute{}.uro_ifc_pset_space_common_uro_net_planned_area xml_real64, uro_ifc_boundary_surface_attribute{}.uro_ifc_pset_space_common_uro_net_planned_area_units xml_buffer, uro_ifc_boundary_surface_attribute{}.uro_ifc_pset_space_common_uro_publicly_accessible xml_boolean, uro_ifc_boundary_surface_attribute{}.uro_ifc_pset_space_common_uro_handicap_accessible xml_boolean, uro_ifc_boundary_surface_attribute{}.uro_ifc_pset_space_common_uro_concealed_flooring xml_boolean, uro_ifc_boundary_surface_attribute{}.uro_ifc_pset_space_common_uro_concealed_ceiling xml_boolean, uro_ifc_boundary_surface_attribute{}.uro_ifc_pset_window_common_uro_reference xml_buffer, uro_ifc_boundary_surface_attribute{}.uro_ifc_pset_window_common_uro_acoustic_rating xml_buffer, uro_ifc_boundary_surface_attribute{}.uro_ifc_pset_window_common_uro_firerating xml_buffer, uro_ifc_boundary_surface_attribute{}.uro_ifc_pset_window_common_uro_security_rating xml_buffer, uro_ifc_boundary_surface_attribute{}.uro_ifc_pset_window_common_uro_is_external xml_boolean, uro_ifc_boundary_surface_attribute{}.uro_ifc_pset_window_common_uro_infiltration xml_real64, uro_ifc_boundary_surface_attribute{}.uro_ifc_pset_window_common_uro_thermal_transmittance xml_real64, uro_ifc_boundary_surface_attribute{}.uro_ifc_pset_window_common_uro_glazing_area_fraction xml_real64,
      uro_ifc_boundary_surface_attribute{}.uro_ifc_pset_window_common_uro_smoke_stop xml_boolean, uro_ifc_boundary_surface_attribute{}.uro_ifc_site_uro_global_id xml_buffer, uro_ifc_boundary_surface_attribute{}.uro_ifc_site_uro_name xml_buffer, uro_ifc_boundary_surface_attribute{}.uro_ifc_site_uro_description xml_buffer, uro_ifc_boundary_surface_attribute{}.uro_ifc_site_uro_object_type xml_buffer, uro_ifc_boundary_surface_attribute{}.uro_ifc_site_uro_long_name xml_buffer, uro_ifc_boundary_surface_attribute{}.uro_ifc_site_uro_composition_type xml_char(7), uro_ifc_boundary_surface_attribute{}.uro_ifc_site_uro_ref_longitude xml_real64, uro_ifc_boundary_surface_attribute{}.uro_ifc_site_uro_ref_latitude xml_real64, uro_ifc_boundary_surface_attribute{}.uro_ifc_site_uro_ref_elevation xml_real64, uro_ifc_boundary_surface_attribute{}.uro_ifc_site_uro_ref_elevation_units xml_buffer, uro_ifc_boundary_surface_attribute{}.uro_ifc_site_uro_land_title_number xml_buffer, uro_ifc_boundary_surface_attribute{}.uro_ifc_site_uro_site_address_xlink_href xml_buffer, uro_ifc_boundary_surface_attribute{}.uro_ifc_space_uro_global_id xml_buffer, uro_ifc_boundary_surface_attribute{}.uro_ifc_space_uro_name xml_buffer, uro_ifc_boundary_surface_attribute{}.uro_ifc_space_uro_description xml_buffer, uro_ifc_boundary_surface_attribute{}.uro_ifc_space_uro_object_type xml_buffer, uro_ifc_boundary_surface_attribute{}.uro_ifc_space_uro_long_name xml_buffer, uro_ifc_boundary_surface_attribute{}.uro_ifc_space_uro_composition_type xml_char(7), uro_ifc_boundary_surface_attribute{}.uro_ifc_space_uro_interioror_exterior_space xml_char(10), uro_ifc_boundary_surface_attribute{}.uro_ifc_space_uro_elevation_with_flooring xml_real64, uro_ifc_boundary_surface_attribute{}.uro_ifc_space_uro_elevation_with_flooring_units xml_buffer, uro_ifc_boundary_surface_attribute{}.uro_ifc_space_base_quantity_uro_nominal_height xml_real64, uro_ifc_boundary_surface_attribute{}.uro_ifc_space_base_quantity_uro_nominal_height_units xml_buffer, uro_ifc_boundary_surface_attribute{}.uro_ifc_space_base_quantity_uro_clear_height xml_real64, uro_ifc_boundary_surface_attribute{}.uro_ifc_space_base_quantity_uro_clear_height_units xml_buffer, uro_ifc_boundary_surface_attribute{}.uro_ifc_space_base_quantity_uro_finish_ceiling_height xml_real64, uro_ifc_boundary_surface_attribute{}.uro_ifc_space_base_quantity_uro_finish_ceiling_height_units xml_buffer, uro_ifc_boundary_surface_attribute{}.uro_ifc_space_base_quantity_uro_gross_perimeter xml_real64, uro_ifc_boundary_surface_attribute{}.uro_ifc_space_base_quantity_uro_gross_perimeter_units xml_buffer,
      uro_ifc_boundary_surface_attribute{}.uro_ifc_space_base_quantity_uro_net_perimeter xml_real64, uro_ifc_boundary_surface_attribute{}.uro_ifc_space_base_quantity_uro_net_perimeter_units xml_buffer, uro_ifc_boundary_surface_attribute{}.uro_ifc_space_base_quantity_uro_gross_ceiling_area xml_real64, uro_ifc_boundary_surface_attribute{}.uro_ifc_space_base_quantity_uro_gross_ceiling_area_units xml_buffer, uro_ifc_boundary_surface_attribute{}.uro_ifc_space_base_quantity_uro_gross_floor_area xml_real64, uro_ifc_boundary_surface_attribute{}.uro_ifc_space_base_quantity_uro_gross_floor_area_units xml_buffer, uro_ifc_boundary_surface_attribute{}.uro_ifc_space_base_quantity_uro_net_ceiling_area xml_real64, uro_ifc_boundary_surface_attribute{}.uro_ifc_space_base_quantity_uro_net_ceiling_area_units xml_buffer, uro_ifc_boundary_surface_attribute{}.uro_ifc_space_base_quantity_uro_net_floor_area xml_real64, uro_ifc_boundary_surface_attribute{}.uro_ifc_space_base_quantity_uro_net_floor_area_units xml_buffer, uro_ifc_boundary_surface_attribute{}.uro_ifc_space_base_quantity_uro_gross_wall_area xml_real64, uro_ifc_boundary_surface_attribute{}.uro_ifc_space_base_quantity_uro_gross_wall_area_units xml_buffer, uro_ifc_boundary_surface_attribute{}.uro_ifc_space_base_quantity_uro_net_wall_area xml_real64, uro_ifc_boundary_surface_attribute{}.uro_ifc_space_base_quantity_uro_net_wall_area_units xml_buffer, uro_ifc_boundary_surface_attribute{}.uro_ifc_space_base_quantity_uro_gross_volume xml_real64, uro_ifc_boundary_surface_attribute{}.uro_ifc_space_base_quantity_uro_gross_volume_units xml_buffer, uro_ifc_boundary_surface_attribute{}.uro_ifc_space_base_quantity_uro_net_volume xml_real64, uro_ifc_boundary_surface_attribute{}.uro_ifc_space_base_quantity_uro_net_volume_units xml_buffer, uro_ifc_boundary_surface_attribute{}.uro_ifc_wall_uro_global_id xml_buffer, uro_ifc_boundary_surface_attribute{}.uro_ifc_wall_uro_name xml_buffer, uro_ifc_boundary_surface_attribute{}.uro_ifc_wall_uro_description xml_buffer, uro_ifc_boundary_surface_attribute{}.uro_ifc_wall_uro_object_type xml_buffer, uro_ifc_boundary_surface_attribute{}.uro_ifc_wall_uro_tag xml_buffer, uro_ifc_boundary_surface_attribute{}.uro_ifc_wall_uro_element_type xml_buffer, uro_ifc_boundary_surface_attribute{}.uro_ifc_wall_uro_element_type_codeSpace xml_buffer, uro_ifc_boundary_surface_attribute{}.uro_ifc_wall_uro_predefined_type xml_buffer, uro_ifc_boundary_surface_attribute{}.uro_ifc_wall_uro_predefined_type_codeSpace xml_buffer, uro_ifc_boundary_surface_attribute{}.uro_ifc_wall_uro_shape_type xml_buffer, uro_ifc_boundary_surface_attribute{}.uro_ifc_wall_uro_shape_type_codeSpace xml_buffer, uro_ifc_boundary_surface_attribute{}.uro_ifc_wall_uro_number_of_riser xml_int64,
      uro_ifc_boundary_surface_attribute{}.uro_ifc_wall_uro_number_of_treads xml_int64, uro_ifc_boundary_surface_attribute{}.uro_ifc_wall_uro_riser_height xml_int64, uro_ifc_boundary_surface_attribute{}.uro_ifc_wall_uro_tread_length xml_int64, uro_ifc_boundary_surface_attribute{}.uro_ifc_wall_uro_operation_type xml_char(11), uro_ifc_boundary_surface_attribute{}.uro_ifc_wall_uro_capacity_by_weight xml_real64, uro_ifc_boundary_surface_attribute{}.uro_ifc_wall_uro_capacity_by_weight_units xml_buffer, uro_ifc_boundary_surface_attribute{}.uro_ifc_wall_uro_capacity_by_number xml_int64, uro_ifc_boundary_surface_attribute{}.uro_ifc_wall_uro_nominal_length xml_real64, uro_ifc_boundary_surface_attribute{}.uro_ifc_wall_uro_nominal_length_units xml_buffer, uro_ifc_boundary_surface_attribute{}.uro_ifc_wall_uro_nominal_width xml_real64, uro_ifc_boundary_surface_attribute{}.uro_ifc_wall_uro_nominal_width_units xml_buffer, uro_ifc_boundary_surface_attribute{}.uro_ifc_wall_uro_nominal_height xml_real64, uro_ifc_boundary_surface_attribute{}.uro_ifc_wall_uro_nominal_height_units xml_buffer, uro_ifc_boundary_surface_attribute{}.uro_ifc_wall_uro_gross_foot_print_area xml_real64, uro_ifc_boundary_surface_attribute{}.uro_ifc_wall_uro_gross_foot_print_area_units xml_buffer, uro_ifc_boundary_surface_attribute{}.uro_ifc_wall_uro_net_foot_print_area xml_real64, uro_ifc_boundary_surface_attribute{}.uro_ifc_wall_uro_net_foot_print_area_units xml_buffer, uro_ifc_boundary_surface_attribute{}.uro_ifc_wall_uro_gross_side_area xml_real64, uro_ifc_boundary_surface_attribute{}.uro_ifc_wall_uro_gross_side_area_units xml_buffer, uro_ifc_boundary_surface_attribute{}.uro_ifc_wall_uro_net_side_area xml_real64, uro_ifc_boundary_surface_attribute{}.uro_ifc_wall_uro_net_side_area_units xml_buffer, uro_ifc_boundary_surface_attribute{}.uro_ifc_wall_uro_gross_side_area_left xml_real64, uro_ifc_boundary_surface_attribute{}.uro_ifc_wall_uro_gross_side_area_left_units xml_buffer, uro_ifc_boundary_surface_attribute{}.uro_ifc_wall_uro_net_side_area_left xml_real64, uro_ifc_boundary_surface_attribute{}.uro_ifc_wall_uro_net_side_area_left_units xml_buffer, uro_ifc_boundary_surface_attribute{}.uro_ifc_wall_uro_gross_side_area_right xml_real64, uro_ifc_boundary_surface_attribute{}.uro_ifc_wall_uro_gross_side_area_right_units xml_buffer, uro_ifc_boundary_surface_attribute{}.uro_ifc_wall_uro_net_side_area_right xml_real64, uro_ifc_boundary_surface_attribute{}.uro_ifc_wall_uro_net_side_area_right_units xml_buffer, uro_ifc_boundary_surface_attribute{}.uro_ifc_wall_uro_gross_volume xml_real64,
      uro_ifc_boundary_surface_attribute{}.uro_ifc_wall_uro_gross_volume_units xml_buffer, uro_ifc_boundary_surface_attribute{}.uro_ifc_wall_uro_net_volume xml_real64, uro_ifc_boundary_surface_attribute{}.uro_ifc_wall_uro_net_volume_units xml_buffer, uro_ifc_boundary_surface_attribute{}.uro_ifc_wall_standard_case_uro_global_id xml_buffer, uro_ifc_boundary_surface_attribute{}.uro_ifc_wall_standard_case_uro_name xml_buffer, uro_ifc_boundary_surface_attribute{}.uro_ifc_wall_standard_case_uro_description xml_buffer, uro_ifc_boundary_surface_attribute{}.uro_ifc_wall_standard_case_uro_object_type xml_buffer, uro_ifc_boundary_surface_attribute{}.uro_ifc_wall_standard_case_uro_tag xml_buffer, uro_ifc_boundary_surface_attribute{}.uro_ifc_wall_standard_case_uro_element_type xml_buffer, uro_ifc_boundary_surface_attribute{}.uro_ifc_wall_standard_case_uro_element_type_codeSpace xml_buffer, uro_ifc_boundary_surface_attribute{}.uro_ifc_wall_standard_case_uro_predefined_type xml_buffer, uro_ifc_boundary_surface_attribute{}.uro_ifc_wall_standard_case_uro_predefined_type_codeSpace xml_buffer, uro_ifc_boundary_surface_attribute{}.uro_ifc_wall_standard_case_uro_shape_type xml_buffer, uro_ifc_boundary_surface_attribute{}.uro_ifc_wall_standard_case_uro_shape_type_codeSpace xml_buffer, uro_ifc_boundary_surface_attribute{}.uro_ifc_wall_standard_case_uro_number_of_riser xml_int64, uro_ifc_boundary_surface_attribute{}.uro_ifc_wall_standard_case_uro_number_of_treads xml_int64, uro_ifc_boundary_surface_attribute{}.uro_ifc_wall_standard_case_uro_riser_height xml_int64, uro_ifc_boundary_surface_attribute{}.uro_ifc_wall_standard_case_uro_tread_length xml_int64, uro_ifc_boundary_surface_attribute{}.uro_ifc_wall_standard_case_uro_operation_type xml_char(11), uro_ifc_boundary_surface_attribute{}.uro_ifc_wall_standard_case_uro_capacity_by_weight xml_real64, uro_ifc_boundary_surface_attribute{}.uro_ifc_wall_standard_case_uro_capacity_by_weight_units xml_buffer, uro_ifc_boundary_surface_attribute{}.uro_ifc_wall_standard_case_uro_capacity_by_number xml_int64, uro_ifc_boundary_surface_attribute{}.uro_ifc_wall_standard_case_uro_nominal_length xml_real64, uro_ifc_boundary_surface_attribute{}.uro_ifc_wall_standard_case_uro_nominal_length_units xml_buffer, uro_ifc_boundary_surface_attribute{}.uro_ifc_wall_standard_case_uro_nominal_width xml_real64, uro_ifc_boundary_surface_attribute{}.uro_ifc_wall_standard_case_uro_nominal_width_units xml_buffer, uro_ifc_boundary_surface_attribute{}.uro_ifc_wall_standard_case_uro_nominal_height xml_real64, uro_ifc_boundary_surface_attribute{}.uro_ifc_wall_standard_case_uro_nominal_height_units xml_buffer, uro_ifc_boundary_surface_attribute{}.uro_ifc_wall_standard_case_uro_gross_foot_print_area xml_real64, uro_ifc_boundary_surface_attribute{}.uro_ifc_wall_standard_case_uro_gross_foot_print_area_units xml_buffer,
      uro_ifc_boundary_surface_attribute{}.uro_ifc_wall_standard_case_uro_net_foot_print_area xml_real64, uro_ifc_boundary_surface_attribute{}.uro_ifc_wall_standard_case_uro_net_foot_print_area_units xml_buffer, uro_ifc_boundary_surface_attribute{}.uro_ifc_wall_standard_case_uro_gross_side_area xml_real64, uro_ifc_boundary_surface_attribute{}.uro_ifc_wall_standard_case_uro_gross_side_area_units xml_buffer, uro_ifc_boundary_surface_attribute{}.uro_ifc_wall_standard_case_uro_net_side_area xml_real64, uro_ifc_boundary_surface_attribute{}.uro_ifc_wall_standard_case_uro_net_side_area_units xml_buffer, uro_ifc_boundary_surface_attribute{}.uro_ifc_wall_standard_case_uro_gross_side_area_left xml_real64, uro_ifc_boundary_surface_attribute{}.uro_ifc_wall_standard_case_uro_gross_side_area_left_units xml_buffer, uro_ifc_boundary_surface_attribute{}.uro_ifc_wall_standard_case_uro_net_side_area_left xml_real64, uro_ifc_boundary_surface_attribute{}.uro_ifc_wall_standard_case_uro_net_side_area_left_units xml_buffer, uro_ifc_boundary_surface_attribute{}.uro_ifc_wall_standard_case_uro_gross_side_area_right xml_real64, uro_ifc_boundary_surface_attribute{}.uro_ifc_wall_standard_case_uro_gross_side_area_right_units xml_buffer, uro_ifc_boundary_surface_attribute{}.uro_ifc_wall_standard_case_uro_net_side_area_right xml_real64, uro_ifc_boundary_surface_attribute{}.uro_ifc_wall_standard_case_uro_net_side_area_right_units xml_buffer, uro_ifc_boundary_surface_attribute{}.uro_ifc_wall_standard_case_uro_gross_volume xml_real64, uro_ifc_boundary_surface_attribute{}.uro_ifc_wall_standard_case_uro_gross_volume_units xml_buffer, uro_ifc_boundary_surface_attribute{}.uro_ifc_wall_standard_case_uro_net_volume xml_real64, uro_ifc_boundary_surface_attribute{}.uro_ifc_wall_standard_case_uro_net_volume_units xml_buffer, uro_ifc_boundary_surface_attribute{}.uro_ifc_window_uro_global_id xml_buffer, uro_ifc_boundary_surface_attribute{}.uro_ifc_window_uro_name xml_buffer, uro_ifc_boundary_surface_attribute{}.uro_ifc_window_uro_description xml_buffer, uro_ifc_boundary_surface_attribute{}.uro_ifc_window_uro_object_type xml_buffer, uro_ifc_boundary_surface_attribute{}.uro_ifc_window_uro_tag xml_buffer, uro_ifc_boundary_surface_attribute{}.uro_ifc_window_uro_element_type xml_buffer, uro_ifc_boundary_surface_attribute{}.uro_ifc_window_uro_element_type_codeSpace xml_buffer, uro_ifc_boundary_surface_attribute{}.uro_ifc_window_uro_predefined_type xml_buffer, uro_ifc_boundary_surface_attribute{}.uro_ifc_window_uro_predefined_type_codeSpace xml_buffer, uro_ifc_boundary_surface_attribute{}.uro_ifc_window_uro_shape_type xml_buffer, uro_ifc_boundary_surface_attribute{}.uro_ifc_window_uro_shape_type_codeSpace xml_buffer, uro_ifc_boundary_surface_attribute{}.uro_ifc_window_uro_number_of_riser xml_int64,
      uro_ifc_boundary_surface_attribute{}.uro_ifc_window_uro_number_of_treads xml_int64, uro_ifc_boundary_surface_attribute{}.uro_ifc_window_uro_riser_height xml_int64, uro_ifc_boundary_surface_attribute{}.uro_ifc_window_uro_tread_length xml_int64, uro_ifc_boundary_surface_attribute{}.uro_ifc_window_uro_operation_type xml_char(11), uro_ifc_boundary_surface_attribute{}.uro_ifc_window_uro_capacity_by_weight xml_real64, uro_ifc_boundary_surface_attribute{}.uro_ifc_window_uro_capacity_by_weight_units xml_buffer, uro_ifc_boundary_surface_attribute{}.uro_ifc_window_uro_capacity_by_number xml_int64, uro_ifc_boundary_surface_attribute{}.uro_ifc_window_uro_overall_height xml_real64, uro_ifc_boundary_surface_attribute{}.uro_ifc_window_uro_overall_height_units xml_buffer, uro_ifc_boundary_surface_attribute{}.uro_ifc_window_uro_overall_width xml_real64, uro_ifc_boundary_surface_attribute{}.uro_ifc_window_uro_overall_width_units xml_buffer
Note: AttributeManager_13 : Input / Room ソリッドに集約
Junction_70
    -> Junction_71
Note: InteriorWallSurface / AttributeManager_7 : Output
Junction_71
    -> AttributeManager_13
Note: #gml_id -> xlink:href / gml_geometry_reversed = Yes
Note: xlink_href とあわせて gml_geometry_reversed = Yes / を trait に設定することにより、 / OrientableSurface (orientation="-") が生成される。
AttributeManager_13
    ATTR_TABLE:
      SET_TO xlink_href = #@Value(gml_id)
      SET_TO gml_geometry_reversed = Yes
      REMOVE gml_id
      REMOVE gml_parent_id
      REMOVE _storey_id
      REMOVE _storey_name
      REMOVE citygml_lod_name
      REMOVE citygml_feature_role
      RENAME_SET_VALUE _room_gml_description > gml_description
      RENAME_SET_VALUE _room_gml_name > gml_name
    -> GeometryPropertySetter_12
GeometryPropertySetter_12
    GQUERY:
      for $geom in //geometry
      where $geom/count(parent::geometry) = 0
      return number($geom/@fme_id)
    OVERWRITE_CHOICE = Yes
    REMOVE_ATTRIBUTE = Yes
    SETTYPE_PARAM = Traits From Attributes
    SRC_ATTRS = xlink_href gml_geometry_reversed
    SET -> GeometryPartExtractor
AttributeRenamer
    ATTR_TABLE:
      RENAME_SET_DEFAULT _room_gml_id > gml_id
      RENAME_SET_DEFAULT _building_id > gml_parent_id
    MISSING_INPUT_ATTRS = REMOVE
    -> AttributeCreator_3
    -> AttributeManager_14
AttributeCreator_3
    ATTR_TABLE:
      SET_TO citygml_lod_name = lod4Solid
      SET_TO citygml_feature_role = interiorRoom
      SET_TO _citygml_feature_type = Room
    -> GeometryPropertySetter_14
GeometryPropertySetter_14
    GQUERY:
      for $geom in //geometry
      where $geom/count(parent::geometry) = 0
      return number($geom/@fme_id)
    OVERWRITE_CHOICE = Yes
    REMOVE_ATTRIBUTE = No
    SETTYPE_PARAM = Traits From Attributes
    SRC_ATTRS = citygml_lod_name
    SET -> PLATEAU.IfcReprojector_10 [IfcFeature]
PLATEAU.IfcReprojector_10
    DEST_COORDSYS = $(DEST_COORDSYS)
    LENGTH_MULTIPLIER = @Value(_lengthmultiplier)
    REPROJECTION_PARAMS = @Value(_reprojection_params)
    Reprojected -> Room (writer CITYGML_2)
Room (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer, citygml_interior_furniture{}.xlink_href xml_buffer, citygml_room_installation{}.xlink_href xml_buffer, uro_ifc_room_attribute{}.uro_ifc_building_uro_global_id xml_buffer, uro_ifc_room_attribute{}.uro_ifc_building_uro_name xml_buffer, uro_ifc_room_attribute{}.uro_ifc_building_uro_description xml_buffer, uro_ifc_room_attribute{}.uro_ifc_building_uro_object_type xml_buffer, uro_ifc_room_attribute{}.uro_ifc_building_uro_long_name xml_buffer, uro_ifc_room_attribute{}.uro_ifc_building_uro_composition_type xml_char(7),
      uro_ifc_room_attribute{}.uro_ifc_building_uro_elevation_of_ref_height xml_real64, uro_ifc_room_attribute{}.uro_ifc_building_uro_elevation_of_ref_height_units xml_buffer, uro_ifc_room_attribute{}.uro_ifc_building_uro_elevation_of_terrain xml_real64, uro_ifc_room_attribute{}.uro_ifc_building_uro_elevation_of_terrain_units xml_buffer, uro_ifc_room_attribute{}.uro_ifc_building_uro_building_address_xlink_href xml_buffer, uro_ifc_room_attribute{}.uro_ifc_building_element_uro_global_id xml_buffer, uro_ifc_room_attribute{}.uro_ifc_building_element_uro_name xml_buffer, uro_ifc_room_attribute{}.uro_ifc_building_element_uro_description xml_buffer, uro_ifc_room_attribute{}.uro_ifc_building_element_uro_object_type xml_buffer, uro_ifc_room_attribute{}.uro_ifc_building_element_uro_tag xml_buffer, uro_ifc_room_attribute{}.uro_ifc_building_element_uro_element_type xml_buffer, uro_ifc_room_attribute{}.uro_ifc_building_element_uro_element_type_codeSpace xml_buffer, uro_ifc_room_attribute{}.uro_ifc_building_element_uro_predefined_type xml_buffer, uro_ifc_room_attribute{}.uro_ifc_building_element_uro_predefined_type_codeSpace xml_buffer, uro_ifc_room_attribute{}.uro_ifc_building_element_uro_shape_type xml_buffer, uro_ifc_room_attribute{}.uro_ifc_building_element_uro_shape_type_codeSpace xml_buffer, uro_ifc_room_attribute{}.uro_ifc_building_element_uro_number_of_riser xml_int64, uro_ifc_room_attribute{}.uro_ifc_building_element_uro_number_of_treads xml_int64, uro_ifc_room_attribute{}.uro_ifc_building_element_uro_riser_height xml_int64, uro_ifc_room_attribute{}.uro_ifc_building_element_uro_tread_length xml_int64, uro_ifc_room_attribute{}.uro_ifc_building_element_uro_operation_type xml_char(11), uro_ifc_room_attribute{}.uro_ifc_building_element_uro_capacity_by_weight xml_real64, uro_ifc_room_attribute{}.uro_ifc_building_element_uro_capacity_by_weight_units xml_buffer, uro_ifc_room_attribute{}.uro_ifc_building_element_uro_capacity_by_number xml_int64, uro_ifc_room_attribute{}.uro_ifc_building_storey_uro_global_id xml_buffer, uro_ifc_room_attribute{}.uro_ifc_building_storey_uro_name xml_buffer, uro_ifc_room_attribute{}.uro_ifc_building_storey_uro_description xml_buffer, uro_ifc_room_attribute{}.uro_ifc_building_storey_uro_object_type xml_buffer, uro_ifc_room_attribute{}.uro_ifc_building_storey_uro_long_name xml_buffer, uro_ifc_room_attribute{}.uro_ifc_building_storey_uro_composition_type xml_char(7),
      uro_ifc_room_attribute{}.uro_ifc_building_storey_uro_elevation xml_real64, uro_ifc_room_attribute{}.uro_ifc_building_storey_uro_elevation_units xml_buffer, uro_ifc_room_attribute{}.uro_ifc_classification_reference_uro_location xml_buffer, uro_ifc_room_attribute{}.uro_ifc_classification_reference_uro_item_reference xml_buffer, uro_ifc_room_attribute{}.uro_ifc_classification_reference_uro_item_reference_codeSpace xml_buffer, uro_ifc_room_attribute{}.uro_ifc_classification_reference_uro_name xml_buffer, uro_ifc_room_attribute{}.uro_ifc_classification_reference_uro_name_codeSpace xml_buffer, uro_ifc_room_attribute{}.uro_ifc_classification_reference_uro_reference_source_uro_ifc_classification_uro_source xml_buffer, uro_ifc_room_attribute{}.uro_ifc_classification_reference_uro_reference_source_uro_ifc_classification_uro_edition xml_buffer, uro_ifc_room_attribute{}.uro_ifc_classification_reference_uro_reference_source_uro_ifc_classification_uro_edition_date xml_date, uro_ifc_room_attribute{}.uro_ifc_classification_reference_uro_reference_source_uro_ifc_classification_uro_name xml_buffer, uro_ifc_room_attribute{}.uro_ifc_coordinate_reference_system_uro_name xml_buffer, uro_ifc_room_attribute{}.uro_ifc_coordinate_reference_system_uro_description xml_buffer, uro_ifc_room_attribute{}.uro_ifc_coordinate_reference_system_uro_geodetic_datum xml_buffer, uro_ifc_room_attribute{}.uro_ifc_coordinate_reference_system_uro_vertical_datum xml_buffer, uro_ifc_room_attribute{}.uro_ifc_curtain_wall_uro_global_id xml_buffer, uro_ifc_room_attribute{}.uro_ifc_curtain_wall_uro_name xml_buffer, uro_ifc_room_attribute{}.uro_ifc_curtain_wall_uro_description xml_buffer, uro_ifc_room_attribute{}.uro_ifc_curtain_wall_uro_object_type xml_buffer, uro_ifc_room_attribute{}.uro_ifc_curtain_wall_uro_tag xml_buffer, uro_ifc_room_attribute{}.uro_ifc_curtain_wall_uro_element_type xml_buffer, uro_ifc_room_attribute{}.uro_ifc_curtain_wall_uro_element_type_codeSpace xml_buffer, uro_ifc_room_attribute{}.uro_ifc_curtain_wall_uro_predefined_type xml_buffer, uro_ifc_room_attribute{}.uro_ifc_curtain_wall_uro_predefined_type_codeSpace xml_buffer, uro_ifc_room_attribute{}.uro_ifc_curtain_wall_uro_shape_type xml_buffer, uro_ifc_room_attribute{}.uro_ifc_curtain_wall_uro_shape_type_codeSpace xml_buffer, uro_ifc_room_attribute{}.uro_ifc_curtain_wall_uro_number_of_riser xml_int64, uro_ifc_room_attribute{}.uro_ifc_curtain_wall_uro_number_of_treads xml_int64, uro_ifc_room_attribute{}.uro_ifc_curtain_wall_uro_riser_height xml_int64, uro_ifc_room_attribute{}.uro_ifc_curtain_wall_uro_tread_length xml_int64,
      uro_ifc_room_attribute{}.uro_ifc_curtain_wall_uro_operation_type xml_char(11), uro_ifc_room_attribute{}.uro_ifc_curtain_wall_uro_capacity_by_weight xml_real64, uro_ifc_room_attribute{}.uro_ifc_curtain_wall_uro_capacity_by_weight_units xml_buffer, uro_ifc_room_attribute{}.uro_ifc_curtain_wall_uro_capacity_by_number xml_int64, uro_ifc_room_attribute{}.uro_ifc_door_uro_global_id xml_buffer, uro_ifc_room_attribute{}.uro_ifc_door_uro_name xml_buffer, uro_ifc_room_attribute{}.uro_ifc_door_uro_description xml_buffer, uro_ifc_room_attribute{}.uro_ifc_door_uro_object_type xml_buffer, uro_ifc_room_attribute{}.uro_ifc_door_uro_tag xml_buffer, uro_ifc_room_attribute{}.uro_ifc_door_uro_element_type xml_buffer, uro_ifc_room_attribute{}.uro_ifc_door_uro_element_type_codeSpace xml_buffer, uro_ifc_room_attribute{}.uro_ifc_door_uro_predefined_type xml_buffer, uro_ifc_room_attribute{}.uro_ifc_door_uro_predefined_type_codeSpace xml_buffer, uro_ifc_room_attribute{}.uro_ifc_door_uro_shape_type xml_buffer, uro_ifc_room_attribute{}.uro_ifc_door_uro_shape_type_codeSpace xml_buffer, uro_ifc_room_attribute{}.uro_ifc_door_uro_number_of_riser xml_int64, uro_ifc_room_attribute{}.uro_ifc_door_uro_number_of_treads xml_int64, uro_ifc_room_attribute{}.uro_ifc_door_uro_riser_height xml_int64, uro_ifc_room_attribute{}.uro_ifc_door_uro_tread_length xml_int64, uro_ifc_room_attribute{}.uro_ifc_door_uro_operation_type xml_char(11), uro_ifc_room_attribute{}.uro_ifc_door_uro_capacity_by_weight xml_real64, uro_ifc_room_attribute{}.uro_ifc_door_uro_capacity_by_weight_units xml_buffer, uro_ifc_room_attribute{}.uro_ifc_door_uro_capacity_by_number xml_int64, uro_ifc_room_attribute{}.uro_ifc_door_uro_overall_height xml_real64, uro_ifc_room_attribute{}.uro_ifc_door_uro_overall_height_units xml_buffer, uro_ifc_room_attribute{}.uro_ifc_door_uro_overall_width xml_real64, uro_ifc_room_attribute{}.uro_ifc_door_uro_overall_width_units xml_buffer, uro_ifc_room_attribute{}.uro_ifc_furnishing_element_uro_global_id xml_buffer, uro_ifc_room_attribute{}.uro_ifc_furnishing_element_uro_name xml_buffer, uro_ifc_room_attribute{}.uro_ifc_furnishing_element_uro_description xml_buffer,
      uro_ifc_room_attribute{}.uro_ifc_furnishing_element_uro_object_type xml_buffer, uro_ifc_room_attribute{}.uro_ifc_furnishing_element_uro_tag xml_buffer, uro_ifc_room_attribute{}.uro_ifc_map_conversion_uro_source_crs_uro_crs_uro_ifc_projected_crs_uro_name xml_buffer, uro_ifc_room_attribute{}.uro_ifc_map_conversion_uro_source_crs_uro_crs_uro_ifc_projected_crs_uro_description xml_buffer, uro_ifc_room_attribute{}.uro_ifc_map_conversion_uro_source_crs_uro_crs_uro_ifc_projected_crs_uro_geodetic_datum xml_buffer, uro_ifc_room_attribute{}.uro_ifc_map_conversion_uro_source_crs_uro_crs_uro_ifc_projected_crs_uro_vertical_datum xml_buffer, uro_ifc_room_attribute{}.uro_ifc_map_conversion_uro_source_crs_uro_crs_uro_ifc_projected_crs_uro_map_unit xml_buffer, uro_ifc_room_attribute{}.uro_ifc_map_conversion_uro_source_crs_uro_crs_uro_ifc_projected_crs_uro_map_projection xml_buffer, uro_ifc_room_attribute{}.uro_ifc_map_conversion_uro_source_crs_uro_crs_uro_ifc_projected_crs_uro_map_zone xml_buffer, uro_ifc_room_attribute{}.uro_ifc_map_conversion_uro_source_crs_uro_crs_uro_ifc_coordinate_reference_system_uro_name xml_buffer, uro_ifc_room_attribute{}.uro_ifc_map_conversion_uro_source_crs_uro_crs_uro_ifc_coordinate_reference_system_uro_description xml_buffer, uro_ifc_room_attribute{}.uro_ifc_map_conversion_uro_source_crs_uro_crs_uro_ifc_coordinate_reference_system_uro_geodetic_datum xml_buffer, uro_ifc_room_attribute{}.uro_ifc_map_conversion_uro_source_crs_uro_crs_uro_ifc_coordinate_reference_system_uro_vertical_datum xml_buffer, uro_ifc_room_attribute{}.uro_ifc_map_conversion_uro_source_crs_uro_context_uro_ifc_geometric_representation_context_uro_context_identifier xml_buffer, uro_ifc_room_attribute{}.uro_ifc_map_conversion_uro_source_crs_uro_context_uro_ifc_geometric_representation_context_uro_context_type xml_buffer, uro_ifc_room_attribute{}.uro_ifc_map_conversion_uro_source_crs_uro_context_uro_ifc_geometric_representation_context_uro_coordinate_space_dimension xml_int64, uro_ifc_room_attribute{}.uro_ifc_map_conversion_uro_source_crs_uro_context_uro_ifc_geometric_representation_context_uro_precision xml_real64, uro_ifc_room_attribute{}.uro_ifc_map_conversion_uro_source_crs_uro_context_uro_ifc_geometric_representation_context_uro_true_north xml_real64, uro_ifc_room_attribute{}.uro_ifc_map_conversion_uro_target_crs_uro_ifc_projected_crs_uro_name xml_buffer, uro_ifc_room_attribute{}.uro_ifc_map_conversion_uro_target_crs_uro_ifc_projected_crs_uro_description xml_buffer, uro_ifc_room_attribute{}.uro_ifc_map_conversion_uro_target_crs_uro_ifc_projected_crs_uro_geodetic_datum xml_buffer, uro_ifc_room_attribute{}.uro_ifc_map_conversion_uro_target_crs_uro_ifc_projected_crs_uro_vertical_datum xml_buffer, uro_ifc_room_attribute{}.uro_ifc_map_conversion_uro_target_crs_uro_ifc_projected_crs_uro_map_unit xml_buffer, uro_ifc_room_attribute{}.uro_ifc_map_conversion_uro_target_crs_uro_ifc_projected_crs_uro_map_projection xml_buffer, uro_ifc_room_attribute{}.uro_ifc_map_conversion_uro_target_crs_uro_ifc_projected_crs_uro_map_zone xml_buffer, uro_ifc_room_attribute{}.uro_ifc_map_conversion_uro_target_crs_uro_ifc_coordinate_reference_system_uro_name xml_buffer, uro_ifc_room_attribute{}.uro_ifc_map_conversion_uro_target_crs_uro_ifc_coordinate_reference_system_uro_description xml_buffer, uro_ifc_room_attribute{}.uro_ifc_map_conversion_uro_target_crs_uro_ifc_coordinate_reference_system_uro_geodetic_datum xml_buffer, uro_ifc_room_attribute{}.uro_ifc_map_conversion_uro_target_crs_uro_ifc_coordinate_reference_system_uro_vertical_datum xml_buffer, uro_ifc_room_attribute{}.uro_ifc_map_conversion_uro_eastings xml_buffer,
      uro_ifc_room_attribute{}.uro_ifc_map_conversion_uro_northings xml_buffer, uro_ifc_room_attribute{}.uro_ifc_map_conversion_uro_orthogonal_height xml_real64, uro_ifc_room_attribute{}.uro_ifc_map_conversion_uro_orthogonal_height_units xml_buffer, uro_ifc_room_attribute{}.uro_ifc_map_conversion_uro_x_axis_abscissa xml_real64, uro_ifc_room_attribute{}.uro_ifc_map_conversion_uro_x_axis_ordinate xml_real64, uro_ifc_room_attribute{}.uro_ifc_map_conversion_uro_scale xml_real64, uro_ifc_room_attribute{}.uro_ifc_opening_element_uro_global_id xml_buffer, uro_ifc_room_attribute{}.uro_ifc_opening_element_uro_name xml_buffer, uro_ifc_room_attribute{}.uro_ifc_opening_element_uro_description xml_buffer, uro_ifc_room_attribute{}.uro_ifc_opening_element_uro_object_type xml_buffer, uro_ifc_room_attribute{}.uro_ifc_opening_element_uro_tag xml_buffer, uro_ifc_room_attribute{}.uro_ifc_opening_element_uro_nominal_area xml_real64, uro_ifc_room_attribute{}.uro_ifc_opening_element_uro_nominal_area_units xml_buffer, uro_ifc_room_attribute{}.uro_ifc_opening_element_uro_nominal_volume xml_real64, uro_ifc_room_attribute{}.uro_ifc_opening_element_uro_nominal_volume_units xml_buffer, uro_ifc_room_attribute{}.uro_ifc_project_uro_global_id xml_buffer, uro_ifc_room_attribute{}.uro_ifc_project_uro_name xml_buffer, uro_ifc_room_attribute{}.uro_ifc_project_uro_description xml_buffer, uro_ifc_room_attribute{}.uro_ifc_project_uro_object_type xml_buffer, uro_ifc_room_attribute{}.uro_ifc_project_uro_long_name xml_buffer, uro_ifc_room_attribute{}.uro_ifc_project_uro_phase xml_buffer, uro_ifc_room_attribute{}.uro_ifc_project_uro_representation_contexts_uro_ifc_geometric_representation_context_uro_context_identifier xml_buffer, uro_ifc_room_attribute{}.uro_ifc_project_uro_representation_contexts_uro_ifc_geometric_representation_context_uro_context_type xml_buffer, uro_ifc_room_attribute{}.uro_ifc_project_uro_representation_contexts_uro_ifc_geometric_representation_context_uro_coordinate_space_dimension xml_int64, uro_ifc_room_attribute{}.uro_ifc_project_uro_representation_contexts_uro_ifc_geometric_representation_context_uro_precision xml_real64, uro_ifc_room_attribute{}.uro_ifc_project_uro_representation_contexts_uro_ifc_geometric_representation_context_uro_true_north xml_real64, uro_ifc_room_attribute{}.uro_ifc_project_uro_units_in_context{}.uro_ifc_unit_uro_dimensions xml_int64, uro_ifc_room_attribute{}.uro_ifc_project_uro_units_in_context{}.uro_ifc_unit_uro_unit_type xml_char(28), uro_ifc_room_attribute{}.uro_ifc_project_uro_units_in_context{}.uro_ifc_unit_uro_perfix xml_buffer, uro_ifc_room_attribute{}.uro_ifc_project_uro_units_in_context{}.uro_ifc_unit_uro_name xml_buffer,
      uro_ifc_room_attribute{}.uro_ifc_projected_crs_uro_name xml_buffer, uro_ifc_room_attribute{}.uro_ifc_projected_crs_uro_description xml_buffer, uro_ifc_room_attribute{}.uro_ifc_projected_crs_uro_geodetic_datum xml_buffer, uro_ifc_room_attribute{}.uro_ifc_projected_crs_uro_vertical_datum xml_buffer, uro_ifc_room_attribute{}.uro_ifc_projected_crs_uro_map_unit xml_buffer, uro_ifc_room_attribute{}.uro_ifc_projected_crs_uro_map_projection xml_buffer, uro_ifc_room_attribute{}.uro_ifc_projected_crs_uro_map_zone xml_buffer, uro_ifc_room_attribute{}.uro_ifc_pset_building_common_uro_building_id xml_real64, uro_ifc_room_attribute{}.uro_ifc_pset_building_common_uro_building_id_units xml_buffer, uro_ifc_room_attribute{}.uro_ifc_pset_building_common_uro_is_permanent_id xml_real64, uro_ifc_room_attribute{}.uro_ifc_pset_building_common_uro_is_permanent_id_units xml_buffer, uro_ifc_room_attribute{}.uro_ifc_pset_building_common_uro_main_fire_use xml_buffer, uro_ifc_room_attribute{}.uro_ifc_pset_building_common_uro_ancillary_fire_use xml_buffer, uro_ifc_room_attribute{}.uro_ifc_pset_building_common_uro_sprinkler_protection xml_boolean, uro_ifc_room_attribute{}.uro_ifc_pset_building_common_uro_sprinkler_protection_automatic xml_boolean, uro_ifc_room_attribute{}.uro_ifc_pset_building_common_uro_occupancy_type xml_buffer, uro_ifc_room_attribute{}.uro_ifc_pset_building_common_uro_occupancy_type_codeSpace xml_buffer, uro_ifc_room_attribute{}.uro_ifc_pset_building_common_uro_gross_planned_area xml_real64, uro_ifc_room_attribute{}.uro_ifc_pset_building_common_uro_gross_planned_area_units xml_buffer, uro_ifc_room_attribute{}.uro_ifc_pset_building_common_uro_number_of_storeys xml_int64, uro_ifc_room_attribute{}.uro_ifc_pset_building_common_uro_year_of_construction xml_buffer, uro_ifc_room_attribute{}.uro_ifc_pset_building_common_uro_is_landmarked xml_boolean, uro_ifc_room_attribute{}.uro_ifc_pset_door_common_uro_reference xml_buffer, uro_ifc_room_attribute{}.uro_ifc_pset_door_common_uro_acoustic_rating xml_buffer, uro_ifc_room_attribute{}.uro_ifc_pset_door_common_uro_firerating xml_buffer, uro_ifc_room_attribute{}.uro_ifc_pset_door_common_uro_security_rating xml_buffer, uro_ifc_room_attribute{}.uro_ifc_pset_door_common_uro_is_external xml_boolean, uro_ifc_room_attribute{}.uro_ifc_pset_door_common_uro_infiltration xml_real64, uro_ifc_room_attribute{}.uro_ifc_pset_door_common_uro_thermal_transmittance xml_real64, uro_ifc_room_attribute{}.uro_ifc_pset_door_common_uro_glazing_area_fraction xml_real64,
      uro_ifc_room_attribute{}.uro_ifc_pset_door_common_uro_handicap_accessible xml_real64, uro_ifc_room_attribute{}.uro_ifc_pset_door_common_uro_fire_exit xml_boolean, uro_ifc_room_attribute{}.uro_ifc_pset_door_common_uro_self_closing xml_real64, uro_ifc_room_attribute{}.uro_ifc_pset_door_common_uro_smoke_stop xml_boolean, uro_ifc_room_attribute{}.uro_ifc_pset_opening_element_common_uro_reference xml_buffer, uro_ifc_room_attribute{}.uro_ifc_pset_opening_element_common_uro_purpose xml_buffer, uro_ifc_room_attribute{}.uro_ifc_pset_opening_element_common_uro_fire_exit xml_boolean, uro_ifc_room_attribute{}.uro_ifc_pset_opening_element_common_uro_protected_opening xml_boolean, uro_ifc_room_attribute{}.uro_ifc_pset_opening_element_common_uro_parallel_jambs xml_boolean, uro_ifc_room_attribute{}.uro_ifc_pset_site_common_uro_buildable_area xml_real64, uro_ifc_room_attribute{}.uro_ifc_pset_site_common_uro_buildable_area_units xml_buffer, uro_ifc_room_attribute{}.uro_ifc_pset_site_common_uro_total_area xml_real64, uro_ifc_room_attribute{}.uro_ifc_pset_site_common_uro_total_area_units xml_buffer, uro_ifc_room_attribute{}.uro_ifc_pset_site_common_uro_building_height_limit xml_real64, uro_ifc_room_attribute{}.uro_ifc_pset_site_common_uro_building_height_limit_units xml_buffer, uro_ifc_room_attribute{}.uro_ifc_pset_space_common_uro_reference xml_buffer, uro_ifc_room_attribute{}.uro_ifc_pset_space_common_uro_category xml_buffer, uro_ifc_room_attribute{}.uro_ifc_pset_space_common_uro_category_codeSpace xml_buffer, uro_ifc_room_attribute{}.uro_ifc_pset_space_common_uro_floor_covering xml_buffer, uro_ifc_room_attribute{}.uro_ifc_pset_space_common_uro_wall_covering xml_buffer, uro_ifc_room_attribute{}.uro_ifc_pset_space_common_uro_ceiling_covering xml_buffer, uro_ifc_room_attribute{}.uro_ifc_pset_space_common_uro_skirting_covering xml_buffer, uro_ifc_room_attribute{}.uro_ifc_pset_space_common_uro_gross_planned_area xml_real64, uro_ifc_room_attribute{}.uro_ifc_pset_space_common_uro_gross_planned_area_units xml_buffer, uro_ifc_room_attribute{}.uro_ifc_pset_space_common_uro_net_planned_area xml_real64, uro_ifc_room_attribute{}.uro_ifc_pset_space_common_uro_net_planned_area_units xml_buffer, uro_ifc_room_attribute{}.uro_ifc_pset_space_common_uro_publicly_accessible xml_boolean, uro_ifc_room_attribute{}.uro_ifc_pset_space_common_uro_handicap_accessible xml_boolean, uro_ifc_room_attribute{}.uro_ifc_pset_space_common_uro_concealed_flooring xml_boolean, uro_ifc_room_attribute{}.uro_ifc_pset_space_common_uro_concealed_ceiling xml_boolean,
      uro_ifc_room_attribute{}.uro_ifc_pset_window_common_uro_reference xml_buffer, uro_ifc_room_attribute{}.uro_ifc_pset_window_common_uro_acoustic_rating xml_buffer, uro_ifc_room_attribute{}.uro_ifc_pset_window_common_uro_firerating xml_buffer, uro_ifc_room_attribute{}.uro_ifc_pset_window_common_uro_security_rating xml_buffer, uro_ifc_room_attribute{}.uro_ifc_pset_window_common_uro_is_external xml_boolean, uro_ifc_room_attribute{}.uro_ifc_pset_window_common_uro_infiltration xml_real64, uro_ifc_room_attribute{}.uro_ifc_pset_window_common_uro_thermal_transmittance xml_real64, uro_ifc_room_attribute{}.uro_ifc_pset_window_common_uro_glazing_area_fraction xml_real64, uro_ifc_room_attribute{}.uro_ifc_pset_window_common_uro_smoke_stop xml_boolean, uro_ifc_room_attribute{}.uro_ifc_site_uro_global_id xml_buffer, uro_ifc_room_attribute{}.uro_ifc_site_uro_name xml_buffer, uro_ifc_room_attribute{}.uro_ifc_site_uro_description xml_buffer, uro_ifc_room_attribute{}.uro_ifc_site_uro_object_type xml_buffer, uro_ifc_room_attribute{}.uro_ifc_site_uro_long_name xml_buffer, uro_ifc_room_attribute{}.uro_ifc_site_uro_composition_type xml_char(7), uro_ifc_room_attribute{}.uro_ifc_site_uro_ref_longitude xml_real64, uro_ifc_room_attribute{}.uro_ifc_site_uro_ref_latitude xml_real64, uro_ifc_room_attribute{}.uro_ifc_site_uro_ref_elevation xml_real64, uro_ifc_room_attribute{}.uro_ifc_site_uro_ref_elevation_units xml_buffer, uro_ifc_room_attribute{}.uro_ifc_site_uro_land_title_number xml_buffer, uro_ifc_room_attribute{}.uro_ifc_site_uro_site_address_xlink_href xml_buffer, uro_ifc_room_attribute{}.uro_ifc_space_uro_global_id xml_buffer, uro_ifc_room_attribute{}.uro_ifc_space_uro_name xml_buffer, uro_ifc_room_attribute{}.uro_ifc_space_uro_description xml_buffer, uro_ifc_room_attribute{}.uro_ifc_space_uro_object_type xml_buffer, uro_ifc_room_attribute{}.uro_ifc_space_uro_long_name xml_buffer, uro_ifc_room_attribute{}.uro_ifc_space_uro_composition_type xml_char(7), uro_ifc_room_attribute{}.uro_ifc_space_uro_interioror_exterior_space xml_char(10), uro_ifc_room_attribute{}.uro_ifc_space_uro_elevation_with_flooring xml_real64, uro_ifc_room_attribute{}.uro_ifc_space_uro_elevation_with_flooring_units xml_buffer,
      uro_ifc_room_attribute{}.uro_ifc_space_base_quantity_uro_nominal_height xml_real64, uro_ifc_room_attribute{}.uro_ifc_space_base_quantity_uro_nominal_height_units xml_buffer, uro_ifc_room_attribute{}.uro_ifc_space_base_quantity_uro_clear_height xml_real64, uro_ifc_room_attribute{}.uro_ifc_space_base_quantity_uro_clear_height_units xml_buffer, uro_ifc_room_attribute{}.uro_ifc_space_base_quantity_uro_finish_ceiling_height xml_real64, uro_ifc_room_attribute{}.uro_ifc_space_base_quantity_uro_finish_ceiling_height_units xml_buffer, uro_ifc_room_attribute{}.uro_ifc_space_base_quantity_uro_gross_perimeter xml_real64, uro_ifc_room_attribute{}.uro_ifc_space_base_quantity_uro_gross_perimeter_units xml_buffer, uro_ifc_room_attribute{}.uro_ifc_space_base_quantity_uro_net_perimeter xml_real64, uro_ifc_room_attribute{}.uro_ifc_space_base_quantity_uro_net_perimeter_units xml_buffer, uro_ifc_room_attribute{}.uro_ifc_space_base_quantity_uro_gross_ceiling_area xml_real64, uro_ifc_room_attribute{}.uro_ifc_space_base_quantity_uro_gross_ceiling_area_units xml_buffer, uro_ifc_room_attribute{}.uro_ifc_space_base_quantity_uro_gross_floor_area xml_real64, uro_ifc_room_attribute{}.uro_ifc_space_base_quantity_uro_gross_floor_area_units xml_buffer, uro_ifc_room_attribute{}.uro_ifc_space_base_quantity_uro_net_ceiling_area xml_real64, uro_ifc_room_attribute{}.uro_ifc_space_base_quantity_uro_net_ceiling_area_units xml_buffer, uro_ifc_room_attribute{}.uro_ifc_space_base_quantity_uro_net_floor_area xml_real64, uro_ifc_room_attribute{}.uro_ifc_space_base_quantity_uro_net_floor_area_units xml_buffer, uro_ifc_room_attribute{}.uro_ifc_space_base_quantity_uro_gross_wall_area xml_real64, uro_ifc_room_attribute{}.uro_ifc_space_base_quantity_uro_gross_wall_area_units xml_buffer, uro_ifc_room_attribute{}.uro_ifc_space_base_quantity_uro_net_wall_area xml_real64, uro_ifc_room_attribute{}.uro_ifc_space_base_quantity_uro_net_wall_area_units xml_buffer, uro_ifc_room_attribute{}.uro_ifc_space_base_quantity_uro_gross_volume xml_real64, uro_ifc_room_attribute{}.uro_ifc_space_base_quantity_uro_gross_volume_units xml_buffer, uro_ifc_room_attribute{}.uro_ifc_space_base_quantity_uro_net_volume xml_real64, uro_ifc_room_attribute{}.uro_ifc_space_base_quantity_uro_net_volume_units xml_buffer, uro_ifc_room_attribute{}.uro_ifc_wall_uro_global_id xml_buffer, uro_ifc_room_attribute{}.uro_ifc_wall_uro_name xml_buffer, uro_ifc_room_attribute{}.uro_ifc_wall_uro_description xml_buffer, uro_ifc_room_attribute{}.uro_ifc_wall_uro_object_type xml_buffer,
      uro_ifc_room_attribute{}.uro_ifc_wall_uro_tag xml_buffer, uro_ifc_room_attribute{}.uro_ifc_wall_uro_element_type xml_buffer, uro_ifc_room_attribute{}.uro_ifc_wall_uro_element_type_codeSpace xml_buffer, uro_ifc_room_attribute{}.uro_ifc_wall_uro_predefined_type xml_buffer, uro_ifc_room_attribute{}.uro_ifc_wall_uro_predefined_type_codeSpace xml_buffer, uro_ifc_room_attribute{}.uro_ifc_wall_uro_shape_type xml_buffer, uro_ifc_room_attribute{}.uro_ifc_wall_uro_shape_type_codeSpace xml_buffer, uro_ifc_room_attribute{}.uro_ifc_wall_uro_number_of_riser xml_int64, uro_ifc_room_attribute{}.uro_ifc_wall_uro_number_of_treads xml_int64, uro_ifc_room_attribute{}.uro_ifc_wall_uro_riser_height xml_int64, uro_ifc_room_attribute{}.uro_ifc_wall_uro_tread_length xml_int64, uro_ifc_room_attribute{}.uro_ifc_wall_uro_operation_type xml_char(11), uro_ifc_room_attribute{}.uro_ifc_wall_uro_capacity_by_weight xml_real64, uro_ifc_room_attribute{}.uro_ifc_wall_uro_capacity_by_weight_units xml_buffer, uro_ifc_room_attribute{}.uro_ifc_wall_uro_capacity_by_number xml_int64, uro_ifc_room_attribute{}.uro_ifc_wall_uro_nominal_length xml_real64, uro_ifc_room_attribute{}.uro_ifc_wall_uro_nominal_length_units xml_buffer, uro_ifc_room_attribute{}.uro_ifc_wall_uro_nominal_width xml_real64, uro_ifc_room_attribute{}.uro_ifc_wall_uro_nominal_width_units xml_buffer, uro_ifc_room_attribute{}.uro_ifc_wall_uro_nominal_height xml_real64, uro_ifc_room_attribute{}.uro_ifc_wall_uro_nominal_height_units xml_buffer, uro_ifc_room_attribute{}.uro_ifc_wall_uro_gross_foot_print_area xml_real64, uro_ifc_room_attribute{}.uro_ifc_wall_uro_gross_foot_print_area_units xml_buffer, uro_ifc_room_attribute{}.uro_ifc_wall_uro_net_foot_print_area xml_real64, uro_ifc_room_attribute{}.uro_ifc_wall_uro_net_foot_print_area_units xml_buffer, uro_ifc_room_attribute{}.uro_ifc_wall_uro_gross_side_area xml_real64, uro_ifc_room_attribute{}.uro_ifc_wall_uro_gross_side_area_units xml_buffer, uro_ifc_room_attribute{}.uro_ifc_wall_uro_net_side_area xml_real64, uro_ifc_room_attribute{}.uro_ifc_wall_uro_net_side_area_units xml_buffer, uro_ifc_room_attribute{}.uro_ifc_wall_uro_gross_side_area_left xml_real64,
      uro_ifc_room_attribute{}.uro_ifc_wall_uro_gross_side_area_left_units xml_buffer, uro_ifc_room_attribute{}.uro_ifc_wall_uro_net_side_area_left xml_real64, uro_ifc_room_attribute{}.uro_ifc_wall_uro_net_side_area_left_units xml_buffer, uro_ifc_room_attribute{}.uro_ifc_wall_uro_gross_side_area_right xml_real64, uro_ifc_room_attribute{}.uro_ifc_wall_uro_gross_side_area_right_units xml_buffer, uro_ifc_room_attribute{}.uro_ifc_wall_uro_net_side_area_right xml_real64, uro_ifc_room_attribute{}.uro_ifc_wall_uro_net_side_area_right_units xml_buffer, uro_ifc_room_attribute{}.uro_ifc_wall_uro_gross_volume xml_real64, uro_ifc_room_attribute{}.uro_ifc_wall_uro_gross_volume_units xml_buffer, uro_ifc_room_attribute{}.uro_ifc_wall_uro_net_volume xml_real64, uro_ifc_room_attribute{}.uro_ifc_wall_uro_net_volume_units xml_buffer, uro_ifc_room_attribute{}.uro_ifc_wall_standard_case_uro_global_id xml_buffer, uro_ifc_room_attribute{}.uro_ifc_wall_standard_case_uro_name xml_buffer, uro_ifc_room_attribute{}.uro_ifc_wall_standard_case_uro_description xml_buffer, uro_ifc_room_attribute{}.uro_ifc_wall_standard_case_uro_object_type xml_buffer, uro_ifc_room_attribute{}.uro_ifc_wall_standard_case_uro_tag xml_buffer, uro_ifc_room_attribute{}.uro_ifc_wall_standard_case_uro_element_type xml_buffer, uro_ifc_room_attribute{}.uro_ifc_wall_standard_case_uro_element_type_codeSpace xml_buffer, uro_ifc_room_attribute{}.uro_ifc_wall_standard_case_uro_predefined_type xml_buffer, uro_ifc_room_attribute{}.uro_ifc_wall_standard_case_uro_predefined_type_codeSpace xml_buffer, uro_ifc_room_attribute{}.uro_ifc_wall_standard_case_uro_shape_type xml_buffer, uro_ifc_room_attribute{}.uro_ifc_wall_standard_case_uro_shape_type_codeSpace xml_buffer, uro_ifc_room_attribute{}.uro_ifc_wall_standard_case_uro_number_of_riser xml_int64, uro_ifc_room_attribute{}.uro_ifc_wall_standard_case_uro_number_of_treads xml_int64, uro_ifc_room_attribute{}.uro_ifc_wall_standard_case_uro_riser_height xml_int64, uro_ifc_room_attribute{}.uro_ifc_wall_standard_case_uro_tread_length xml_int64, uro_ifc_room_attribute{}.uro_ifc_wall_standard_case_uro_operation_type xml_char(11), uro_ifc_room_attribute{}.uro_ifc_wall_standard_case_uro_capacity_by_weight xml_real64, uro_ifc_room_attribute{}.uro_ifc_wall_standard_case_uro_capacity_by_weight_units xml_buffer, uro_ifc_room_attribute{}.uro_ifc_wall_standard_case_uro_capacity_by_number xml_int64,
      uro_ifc_room_attribute{}.uro_ifc_wall_standard_case_uro_nominal_length xml_real64, uro_ifc_room_attribute{}.uro_ifc_wall_standard_case_uro_nominal_length_units xml_buffer, uro_ifc_room_attribute{}.uro_ifc_wall_standard_case_uro_nominal_width xml_real64, uro_ifc_room_attribute{}.uro_ifc_wall_standard_case_uro_nominal_width_units xml_buffer, uro_ifc_room_attribute{}.uro_ifc_wall_standard_case_uro_nominal_height xml_real64, uro_ifc_room_attribute{}.uro_ifc_wall_standard_case_uro_nominal_height_units xml_buffer, uro_ifc_room_attribute{}.uro_ifc_wall_standard_case_uro_gross_foot_print_area xml_real64, uro_ifc_room_attribute{}.uro_ifc_wall_standard_case_uro_gross_foot_print_area_units xml_buffer, uro_ifc_room_attribute{}.uro_ifc_wall_standard_case_uro_net_foot_print_area xml_real64, uro_ifc_room_attribute{}.uro_ifc_wall_standard_case_uro_net_foot_print_area_units xml_buffer, uro_ifc_room_attribute{}.uro_ifc_wall_standard_case_uro_gross_side_area xml_real64, uro_ifc_room_attribute{}.uro_ifc_wall_standard_case_uro_gross_side_area_units xml_buffer, uro_ifc_room_attribute{}.uro_ifc_wall_standard_case_uro_net_side_area xml_real64, uro_ifc_room_attribute{}.uro_ifc_wall_standard_case_uro_net_side_area_units xml_buffer, uro_ifc_room_attribute{}.uro_ifc_wall_standard_case_uro_gross_side_area_left xml_real64, uro_ifc_room_attribute{}.uro_ifc_wall_standard_case_uro_gross_side_area_left_units xml_buffer, uro_ifc_room_attribute{}.uro_ifc_wall_standard_case_uro_net_side_area_left xml_real64, uro_ifc_room_attribute{}.uro_ifc_wall_standard_case_uro_net_side_area_left_units xml_buffer, uro_ifc_room_attribute{}.uro_ifc_wall_standard_case_uro_gross_side_area_right xml_real64, uro_ifc_room_attribute{}.uro_ifc_wall_standard_case_uro_gross_side_area_right_units xml_buffer, uro_ifc_room_attribute{}.uro_ifc_wall_standard_case_uro_net_side_area_right xml_real64, uro_ifc_room_attribute{}.uro_ifc_wall_standard_case_uro_net_side_area_right_units xml_buffer, uro_ifc_room_attribute{}.uro_ifc_wall_standard_case_uro_gross_volume xml_real64, uro_ifc_room_attribute{}.uro_ifc_wall_standard_case_uro_gross_volume_units xml_buffer, uro_ifc_room_attribute{}.uro_ifc_wall_standard_case_uro_net_volume xml_real64, uro_ifc_room_attribute{}.uro_ifc_wall_standard_case_uro_net_volume_units xml_buffer, uro_ifc_room_attribute{}.uro_ifc_window_uro_global_id xml_buffer, uro_ifc_room_attribute{}.uro_ifc_window_uro_name xml_buffer, uro_ifc_room_attribute{}.uro_ifc_window_uro_description xml_buffer, uro_ifc_room_attribute{}.uro_ifc_window_uro_object_type xml_buffer,
      uro_ifc_room_attribute{}.uro_ifc_window_uro_tag xml_buffer, uro_ifc_room_attribute{}.uro_ifc_window_uro_element_type xml_buffer, uro_ifc_room_attribute{}.uro_ifc_window_uro_element_type_codeSpace xml_buffer, uro_ifc_room_attribute{}.uro_ifc_window_uro_predefined_type xml_buffer, uro_ifc_room_attribute{}.uro_ifc_window_uro_predefined_type_codeSpace xml_buffer, uro_ifc_room_attribute{}.uro_ifc_window_uro_shape_type xml_buffer, uro_ifc_room_attribute{}.uro_ifc_window_uro_shape_type_codeSpace xml_buffer, uro_ifc_room_attribute{}.uro_ifc_window_uro_number_of_riser xml_int64, uro_ifc_room_attribute{}.uro_ifc_window_uro_number_of_treads xml_int64, uro_ifc_room_attribute{}.uro_ifc_window_uro_riser_height xml_int64, uro_ifc_room_attribute{}.uro_ifc_window_uro_tread_length xml_int64, uro_ifc_room_attribute{}.uro_ifc_window_uro_operation_type xml_char(11), uro_ifc_room_attribute{}.uro_ifc_window_uro_capacity_by_weight xml_real64, uro_ifc_room_attribute{}.uro_ifc_window_uro_capacity_by_weight_units xml_buffer, uro_ifc_room_attribute{}.uro_ifc_window_uro_capacity_by_number xml_int64, uro_ifc_room_attribute{}.uro_ifc_window_uro_overall_height xml_real64, uro_ifc_room_attribute{}.uro_ifc_window_uro_overall_height_units xml_buffer, uro_ifc_room_attribute{}.uro_ifc_window_uro_overall_width xml_real64, uro_ifc_room_attribute{}.uro_ifc_window_uro_overall_width_units xml_buffer, uro_room_data_quality_attribute{}.uro_room_data_quality_attribute_uro_src_scale{} xml_buffer, uro_room_data_quality_attribute{}.uro_room_data_quality_attribute_uro_src_scale{}.codeSpace xml_buffer, uro_room_data_quality_attribute{}.uro_room_data_quality_attribute_uro_geometry_src_desc{} xml_buffer, uro_room_data_quality_attribute{}.uro_room_data_quality_attribute_uro_geometry_src_desc{}.codeSpace xml_buffer, uro_room_data_quality_attribute{}.uro_room_data_quality_attribute_uro_thematic_src_desc{} xml_buffer, uro_room_data_quality_attribute{}.uro_room_data_quality_attribute_uro_thematic_src_desc{}.codeSpace xml_buffer, uro_room_data_quality_attribute{}.uro_room_data_quality_attribute_uro_appearance_src_desc{} xml_buffer, uro_room_data_quality_attribute{}.uro_room_data_quality_attribute_uro_appearance_src_desc{}.codeSpace xml_buffer, uro_room_data_quality_attribute{}.uro_room_data_quality_attribute_uro_lod_type{} xml_char(3)
AttributeManager_14
    ATTR_TABLE:
      REMOVE gml_parent_id
      RENAME_SET_VALUE gml_id > gml_parent_id
      REMOVE _citygml_feature_type
      REMOVE _parent_feature_type
      REMOVE fme_feature_type
      RENAME_SET_VALUE _room_ifc_unique_id > ifc_parent_unique_id
    USER_EXPOSED_ATTRIBUTES = ifc_unique_id,_room_ifc_unique_id
    -> Junction_43
Note: FeatureMerger_5 : Supplier
Junction_43
    -> Junction_48
Tester_IfcBeam
    BOOL_OP = OR
    TEST_CLAUSE = TEST $(DEST_LOD) = 4.3
    TEST_MODE = TEST
    PASSED -> Junction_40
Tester_IfcRailing
    BOOL_OP = OR
    TEST_CLAUSE = TEST $(DEST_LOD) = 4.3
    TEST_MODE = TEST
    PASSED -> Junction_40
Junction_66
    -> Junction_40
Note: GeometryExtractor_4
Junction_40
    -> Junction_44
Note: IfcStair / IfcStairFlight / IfcRamp / IfcRailing / IfcBuildingElementProxy / IfcTransportElement
Junction_44
    -> GeometryRefiner_2
GeometryRefiner_2
    -> GeometryExtractor_4
GeometryExtractor_4
    ATTR = _geometry
    KIND_LONG = FME Binary
    REMOVE_GEOMETRY = No
    -> SurfaceFootprintReplacer_8
SurfaceFootprintReplacer_8
    OFFSET_Z = 0
    SHADOW_MODE = Overhead Shadow
    FOOTPRINT -> SpatialFilter_5 [Candidate]
    <REJECTED> -> Junction_47
SpatialFilter_5
    AGGREGATE_HANDLING = Yes
    BASE_TYPE = Multiple Filters
    CURVE_BOUNDARY_RULE_PARAM = Default Rule
    GROUP_BY = _building_id _storey_id
    PASS_CRITERIA = Pass Against One Filter
    PREDATTR = _predicate
    PREDICATES = CONTAINS
    USE_BOUNDING_BOX = No
    PASSED -> GeometryReplacer_4
    FAILED -> GeometryReplacer_5
GeometryReplacer_4
    KIND_LONG = FME Binary
    REMOVE_ATTRIBUTE = Yes
    SOURCE = @Value(_geometry)
    -> AttributeFilter_2
AttributeCreator_15
    ATTR_TABLE:
      SET_TO gml_id = inst_@UUID()
      SET_TO gml_parent_id = @Value(_building_id)
      SET_TO citygml_lod_name = lod4Geometry
      SET_TO citygml_feature_role = interiorBuildingInstallation
      SET_TO _citygml_feature_type = IntBuildingInstallation
    -> GeometryPropertySetter_8
GeometryPropertySetter_8
    GQUERY:
      for $geom in //geometry
      where $geom/count(parent::geometry) = 0
      return number($geom/@fme_id)
    OVERWRITE_CHOICE = Yes
    REMOVE_ATTRIBUTE = No
    SETTYPE_PARAM = Traits From Attributes
    SRC_ATTRS = citygml_lod_name
    SET -> PLATEAU.IfcReprojector_2 [IfcFeature]
PLATEAU.IfcReprojector_2
    DEST_COORDSYS = $(DEST_COORDSYS)
    LENGTH_MULTIPLIER = @Value(_lengthmultiplier)
    REPROJECTION_PARAMS = @Value(_reprojection_params)
    Reprojected -> IntBuildingInstallation (writer CITYGML_2)
IntBuildingInstallation (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer, uro_ifc_int_building_installation_attribute{}.uro_ifc_building_uro_global_id xml_buffer, uro_ifc_int_building_installation_attribute{}.uro_ifc_building_uro_name xml_buffer, uro_ifc_int_building_installation_attribute{}.uro_ifc_building_uro_description xml_buffer, uro_ifc_int_building_installation_attribute{}.uro_ifc_building_uro_object_type xml_buffer, uro_ifc_int_building_installation_attribute{}.uro_ifc_building_uro_long_name xml_buffer, uro_ifc_int_building_installation_attribute{}.uro_ifc_building_uro_composition_type xml_char(7), uro_ifc_int_building_installation_attribute{}.uro_ifc_building_uro_elevation_of_ref_height xml_real64, uro_ifc_int_building_installation_attribute{}.uro_ifc_building_uro_elevation_of_ref_height_units xml_buffer,
      uro_ifc_int_building_installation_attribute{}.uro_ifc_building_uro_elevation_of_terrain xml_real64, uro_ifc_int_building_installation_attribute{}.uro_ifc_building_uro_elevation_of_terrain_units xml_buffer, uro_ifc_int_building_installation_attribute{}.uro_ifc_building_uro_building_address_xlink_href xml_buffer, uro_ifc_int_building_installation_attribute{}.uro_ifc_building_element_uro_global_id xml_buffer, uro_ifc_int_building_installation_attribute{}.uro_ifc_building_element_uro_name xml_buffer, uro_ifc_int_building_installation_attribute{}.uro_ifc_building_element_uro_description xml_buffer, uro_ifc_int_building_installation_attribute{}.uro_ifc_building_element_uro_object_type xml_buffer, uro_ifc_int_building_installation_attribute{}.uro_ifc_building_element_uro_tag xml_buffer, uro_ifc_int_building_installation_attribute{}.uro_ifc_building_element_uro_element_type xml_buffer, uro_ifc_int_building_installation_attribute{}.uro_ifc_building_element_uro_element_type_codeSpace xml_buffer, uro_ifc_int_building_installation_attribute{}.uro_ifc_building_element_uro_predefined_type xml_buffer, uro_ifc_int_building_installation_attribute{}.uro_ifc_building_element_uro_predefined_type_codeSpace xml_buffer, uro_ifc_int_building_installation_attribute{}.uro_ifc_building_element_uro_shape_type xml_buffer, uro_ifc_int_building_installation_attribute{}.uro_ifc_building_element_uro_shape_type_codeSpace xml_buffer, uro_ifc_int_building_installation_attribute{}.uro_ifc_building_element_uro_number_of_riser xml_int64, uro_ifc_int_building_installation_attribute{}.uro_ifc_building_element_uro_number_of_treads xml_int64, uro_ifc_int_building_installation_attribute{}.uro_ifc_building_element_uro_riser_height xml_int64, uro_ifc_int_building_installation_attribute{}.uro_ifc_building_element_uro_tread_length xml_int64, uro_ifc_int_building_installation_attribute{}.uro_ifc_building_element_uro_operation_type xml_char(11), uro_ifc_int_building_installation_attribute{}.uro_ifc_building_element_uro_capacity_by_weight xml_real64, uro_ifc_int_building_installation_attribute{}.uro_ifc_building_element_uro_capacity_by_weight_units xml_buffer, uro_ifc_int_building_installation_attribute{}.uro_ifc_building_element_uro_capacity_by_number xml_int64, uro_ifc_int_building_installation_attribute{}.uro_ifc_building_storey_uro_global_id xml_buffer, uro_ifc_int_building_installation_attribute{}.uro_ifc_building_storey_uro_name xml_buffer, uro_ifc_int_building_installation_attribute{}.uro_ifc_building_storey_uro_description xml_buffer, uro_ifc_int_building_installation_attribute{}.uro_ifc_building_storey_uro_object_type xml_buffer, uro_ifc_int_building_installation_attribute{}.uro_ifc_building_storey_uro_long_name xml_buffer, uro_ifc_int_building_installation_attribute{}.uro_ifc_building_storey_uro_composition_type xml_char(7), uro_ifc_int_building_installation_attribute{}.uro_ifc_building_storey_uro_elevation xml_real64, uro_ifc_int_building_installation_attribute{}.uro_ifc_building_storey_uro_elevation_units xml_buffer,
      uro_ifc_int_building_installation_attribute{}.uro_ifc_classification_reference_uro_location xml_buffer, uro_ifc_int_building_installation_attribute{}.uro_ifc_classification_reference_uro_item_reference xml_buffer, uro_ifc_int_building_installation_attribute{}.uro_ifc_classification_reference_uro_item_reference_codeSpace xml_buffer, uro_ifc_int_building_installation_attribute{}.uro_ifc_classification_reference_uro_name xml_buffer, uro_ifc_int_building_installation_attribute{}.uro_ifc_classification_reference_uro_name_codeSpace xml_buffer, uro_ifc_int_building_installation_attribute{}.uro_ifc_classification_reference_uro_reference_source_uro_ifc_classification_uro_source xml_buffer, uro_ifc_int_building_installation_attribute{}.uro_ifc_classification_reference_uro_reference_source_uro_ifc_classification_uro_edition xml_buffer, uro_ifc_int_building_installation_attribute{}.uro_ifc_classification_reference_uro_reference_source_uro_ifc_classification_uro_edition_date xml_date, uro_ifc_int_building_installation_attribute{}.uro_ifc_classification_reference_uro_reference_source_uro_ifc_classification_uro_name xml_buffer, uro_ifc_int_building_installation_attribute{}.uro_ifc_coordinate_reference_system_uro_name xml_buffer, uro_ifc_int_building_installation_attribute{}.uro_ifc_coordinate_reference_system_uro_description xml_buffer, uro_ifc_int_building_installation_attribute{}.uro_ifc_coordinate_reference_system_uro_geodetic_datum xml_buffer, uro_ifc_int_building_installation_attribute{}.uro_ifc_coordinate_reference_system_uro_vertical_datum xml_buffer, uro_ifc_int_building_installation_attribute{}.uro_ifc_curtain_wall_uro_global_id xml_buffer, uro_ifc_int_building_installation_attribute{}.uro_ifc_curtain_wall_uro_name xml_buffer, uro_ifc_int_building_installation_attribute{}.uro_ifc_curtain_wall_uro_description xml_buffer, uro_ifc_int_building_installation_attribute{}.uro_ifc_curtain_wall_uro_object_type xml_buffer, uro_ifc_int_building_installation_attribute{}.uro_ifc_curtain_wall_uro_tag xml_buffer, uro_ifc_int_building_installation_attribute{}.uro_ifc_curtain_wall_uro_element_type xml_buffer, uro_ifc_int_building_installation_attribute{}.uro_ifc_curtain_wall_uro_element_type_codeSpace xml_buffer, uro_ifc_int_building_installation_attribute{}.uro_ifc_curtain_wall_uro_predefined_type xml_buffer, uro_ifc_int_building_installation_attribute{}.uro_ifc_curtain_wall_uro_predefined_type_codeSpace xml_buffer, uro_ifc_int_building_installation_attribute{}.uro_ifc_curtain_wall_uro_shape_type xml_buffer, uro_ifc_int_building_installation_attribute{}.uro_ifc_curtain_wall_uro_shape_type_codeSpace xml_buffer, uro_ifc_int_building_installation_attribute{}.uro_ifc_curtain_wall_uro_number_of_riser xml_int64, uro_ifc_int_building_installation_attribute{}.uro_ifc_curtain_wall_uro_number_of_treads xml_int64, uro_ifc_int_building_installation_attribute{}.uro_ifc_curtain_wall_uro_riser_height xml_int64, uro_ifc_int_building_installation_attribute{}.uro_ifc_curtain_wall_uro_tread_length xml_int64, uro_ifc_int_building_installation_attribute{}.uro_ifc_curtain_wall_uro_operation_type xml_char(11), uro_ifc_int_building_installation_attribute{}.uro_ifc_curtain_wall_uro_capacity_by_weight xml_real64,
      uro_ifc_int_building_installation_attribute{}.uro_ifc_curtain_wall_uro_capacity_by_weight_units xml_buffer, uro_ifc_int_building_installation_attribute{}.uro_ifc_curtain_wall_uro_capacity_by_number xml_int64, uro_ifc_int_building_installation_attribute{}.uro_ifc_door_uro_global_id xml_buffer, uro_ifc_int_building_installation_attribute{}.uro_ifc_door_uro_name xml_buffer, uro_ifc_int_building_installation_attribute{}.uro_ifc_door_uro_description xml_buffer, uro_ifc_int_building_installation_attribute{}.uro_ifc_door_uro_object_type xml_buffer, uro_ifc_int_building_installation_attribute{}.uro_ifc_door_uro_tag xml_buffer, uro_ifc_int_building_installation_attribute{}.uro_ifc_door_uro_element_type xml_buffer, uro_ifc_int_building_installation_attribute{}.uro_ifc_door_uro_element_type_codeSpace xml_buffer, uro_ifc_int_building_installation_attribute{}.uro_ifc_door_uro_predefined_type xml_buffer, uro_ifc_int_building_installation_attribute{}.uro_ifc_door_uro_predefined_type_codeSpace xml_buffer, uro_ifc_int_building_installation_attribute{}.uro_ifc_door_uro_shape_type xml_buffer, uro_ifc_int_building_installation_attribute{}.uro_ifc_door_uro_shape_type_codeSpace xml_buffer, uro_ifc_int_building_installation_attribute{}.uro_ifc_door_uro_number_of_riser xml_int64, uro_ifc_int_building_installation_attribute{}.uro_ifc_door_uro_number_of_treads xml_int64, uro_ifc_int_building_installation_attribute{}.uro_ifc_door_uro_riser_height xml_int64, uro_ifc_int_building_installation_attribute{}.uro_ifc_door_uro_tread_length xml_int64, uro_ifc_int_building_installation_attribute{}.uro_ifc_door_uro_operation_type xml_char(11), uro_ifc_int_building_installation_attribute{}.uro_ifc_door_uro_capacity_by_weight xml_real64, uro_ifc_int_building_installation_attribute{}.uro_ifc_door_uro_capacity_by_weight_units xml_buffer, uro_ifc_int_building_installation_attribute{}.uro_ifc_door_uro_capacity_by_number xml_int64, uro_ifc_int_building_installation_attribute{}.uro_ifc_door_uro_overall_height xml_real64, uro_ifc_int_building_installation_attribute{}.uro_ifc_door_uro_overall_height_units xml_buffer, uro_ifc_int_building_installation_attribute{}.uro_ifc_door_uro_overall_width xml_real64, uro_ifc_int_building_installation_attribute{}.uro_ifc_door_uro_overall_width_units xml_buffer, uro_ifc_int_building_installation_attribute{}.uro_ifc_furnishing_element_uro_global_id xml_buffer, uro_ifc_int_building_installation_attribute{}.uro_ifc_furnishing_element_uro_name xml_buffer, uro_ifc_int_building_installation_attribute{}.uro_ifc_furnishing_element_uro_description xml_buffer, uro_ifc_int_building_installation_attribute{}.uro_ifc_furnishing_element_uro_object_type xml_buffer, uro_ifc_int_building_installation_attribute{}.uro_ifc_furnishing_element_uro_tag xml_buffer,
      uro_ifc_int_building_installation_attribute{}.uro_ifc_map_conversion_uro_source_crs_uro_crs_uro_ifc_projected_crs_uro_name xml_buffer, uro_ifc_int_building_installation_attribute{}.uro_ifc_map_conversion_uro_source_crs_uro_crs_uro_ifc_projected_crs_uro_description xml_buffer, uro_ifc_int_building_installation_attribute{}.uro_ifc_map_conversion_uro_source_crs_uro_crs_uro_ifc_projected_crs_uro_geodetic_datum xml_buffer, uro_ifc_int_building_installation_attribute{}.uro_ifc_map_conversion_uro_source_crs_uro_crs_uro_ifc_projected_crs_uro_vertical_datum xml_buffer, uro_ifc_int_building_installation_attribute{}.uro_ifc_map_conversion_uro_source_crs_uro_crs_uro_ifc_projected_crs_uro_map_unit xml_buffer, uro_ifc_int_building_installation_attribute{}.uro_ifc_map_conversion_uro_source_crs_uro_crs_uro_ifc_projected_crs_uro_map_projection xml_buffer, uro_ifc_int_building_installation_attribute{}.uro_ifc_map_conversion_uro_source_crs_uro_crs_uro_ifc_projected_crs_uro_map_zone xml_buffer, uro_ifc_int_building_installation_attribute{}.uro_ifc_map_conversion_uro_source_crs_uro_crs_uro_ifc_coordinate_reference_system_uro_name xml_buffer, uro_ifc_int_building_installation_attribute{}.uro_ifc_map_conversion_uro_source_crs_uro_crs_uro_ifc_coordinate_reference_system_uro_description xml_buffer, uro_ifc_int_building_installation_attribute{}.uro_ifc_map_conversion_uro_source_crs_uro_crs_uro_ifc_coordinate_reference_system_uro_geodetic_datum xml_buffer, uro_ifc_int_building_installation_attribute{}.uro_ifc_map_conversion_uro_source_crs_uro_crs_uro_ifc_coordinate_reference_system_uro_vertical_datum xml_buffer, uro_ifc_int_building_installation_attribute{}.uro_ifc_map_conversion_uro_source_crs_uro_context_uro_ifc_geometric_representation_context_uro_context_identifier xml_buffer, uro_ifc_int_building_installation_attribute{}.uro_ifc_map_conversion_uro_source_crs_uro_context_uro_ifc_geometric_representation_context_uro_context_type xml_buffer, uro_ifc_int_building_installation_attribute{}.uro_ifc_map_conversion_uro_source_crs_uro_context_uro_ifc_geometric_representation_context_uro_coordinate_space_dimension xml_int64, uro_ifc_int_building_installation_attribute{}.uro_ifc_map_conversion_uro_source_crs_uro_context_uro_ifc_geometric_representation_context_uro_precision xml_real64, uro_ifc_int_building_installation_attribute{}.uro_ifc_map_conversion_uro_source_crs_uro_context_uro_ifc_geometric_representation_context_uro_true_north xml_real64, uro_ifc_int_building_installation_attribute{}.uro_ifc_map_conversion_uro_target_crs_uro_ifc_projected_crs_uro_name xml_buffer, uro_ifc_int_building_installation_attribute{}.uro_ifc_map_conversion_uro_target_crs_uro_ifc_projected_crs_uro_description xml_buffer, uro_ifc_int_building_installation_attribute{}.uro_ifc_map_conversion_uro_target_crs_uro_ifc_projected_crs_uro_geodetic_datum xml_buffer, uro_ifc_int_building_installation_attribute{}.uro_ifc_map_conversion_uro_target_crs_uro_ifc_projected_crs_uro_vertical_datum xml_buffer, uro_ifc_int_building_installation_attribute{}.uro_ifc_map_conversion_uro_target_crs_uro_ifc_projected_crs_uro_map_unit xml_buffer, uro_ifc_int_building_installation_attribute{}.uro_ifc_map_conversion_uro_target_crs_uro_ifc_projected_crs_uro_map_projection xml_buffer, uro_ifc_int_building_installation_attribute{}.uro_ifc_map_conversion_uro_target_crs_uro_ifc_projected_crs_uro_map_zone xml_buffer, uro_ifc_int_building_installation_attribute{}.uro_ifc_map_conversion_uro_target_crs_uro_ifc_coordinate_reference_system_uro_name xml_buffer, uro_ifc_int_building_installation_attribute{}.uro_ifc_map_conversion_uro_target_crs_uro_ifc_coordinate_reference_system_uro_description xml_buffer, uro_ifc_int_building_installation_attribute{}.uro_ifc_map_conversion_uro_target_crs_uro_ifc_coordinate_reference_system_uro_geodetic_datum xml_buffer, uro_ifc_int_building_installation_attribute{}.uro_ifc_map_conversion_uro_target_crs_uro_ifc_coordinate_reference_system_uro_vertical_datum xml_buffer, uro_ifc_int_building_installation_attribute{}.uro_ifc_map_conversion_uro_eastings xml_buffer, uro_ifc_int_building_installation_attribute{}.uro_ifc_map_conversion_uro_northings xml_buffer, uro_ifc_int_building_installation_attribute{}.uro_ifc_map_conversion_uro_orthogonal_height xml_real64,
      uro_ifc_int_building_installation_attribute{}.uro_ifc_map_conversion_uro_orthogonal_height_units xml_buffer, uro_ifc_int_building_installation_attribute{}.uro_ifc_map_conversion_uro_x_axis_abscissa xml_real64, uro_ifc_int_building_installation_attribute{}.uro_ifc_map_conversion_uro_x_axis_ordinate xml_real64, uro_ifc_int_building_installation_attribute{}.uro_ifc_map_conversion_uro_scale xml_real64, uro_ifc_int_building_installation_attribute{}.uro_ifc_opening_element_uro_global_id xml_buffer, uro_ifc_int_building_installation_attribute{}.uro_ifc_opening_element_uro_name xml_buffer, uro_ifc_int_building_installation_attribute{}.uro_ifc_opening_element_uro_description xml_buffer, uro_ifc_int_building_installation_attribute{}.uro_ifc_opening_element_uro_object_type xml_buffer, uro_ifc_int_building_installation_attribute{}.uro_ifc_opening_element_uro_tag xml_buffer, uro_ifc_int_building_installation_attribute{}.uro_ifc_opening_element_uro_nominal_area xml_real64, uro_ifc_int_building_installation_attribute{}.uro_ifc_opening_element_uro_nominal_area_units xml_buffer, uro_ifc_int_building_installation_attribute{}.uro_ifc_opening_element_uro_nominal_volume xml_real64, uro_ifc_int_building_installation_attribute{}.uro_ifc_opening_element_uro_nominal_volume_units xml_buffer, uro_ifc_int_building_installation_attribute{}.uro_ifc_project_uro_global_id xml_buffer, uro_ifc_int_building_installation_attribute{}.uro_ifc_project_uro_name xml_buffer, uro_ifc_int_building_installation_attribute{}.uro_ifc_project_uro_description xml_buffer, uro_ifc_int_building_installation_attribute{}.uro_ifc_project_uro_object_type xml_buffer, uro_ifc_int_building_installation_attribute{}.uro_ifc_project_uro_long_name xml_buffer, uro_ifc_int_building_installation_attribute{}.uro_ifc_project_uro_phase xml_buffer, uro_ifc_int_building_installation_attribute{}.uro_ifc_project_uro_representation_contexts_uro_ifc_geometric_representation_context_uro_context_identifier xml_buffer, uro_ifc_int_building_installation_attribute{}.uro_ifc_project_uro_representation_contexts_uro_ifc_geometric_representation_context_uro_context_type xml_buffer, uro_ifc_int_building_installation_attribute{}.uro_ifc_project_uro_representation_contexts_uro_ifc_geometric_representation_context_uro_coordinate_space_dimension xml_int64, uro_ifc_int_building_installation_attribute{}.uro_ifc_project_uro_representation_contexts_uro_ifc_geometric_representation_context_uro_precision xml_real64, uro_ifc_int_building_installation_attribute{}.uro_ifc_project_uro_representation_contexts_uro_ifc_geometric_representation_context_uro_true_north xml_real64, uro_ifc_int_building_installation_attribute{}.uro_ifc_project_uro_units_in_context{}.uro_ifc_unit_uro_dimensions xml_int64, uro_ifc_int_building_installation_attribute{}.uro_ifc_project_uro_units_in_context{}.uro_ifc_unit_uro_unit_type xml_char(28), uro_ifc_int_building_installation_attribute{}.uro_ifc_project_uro_units_in_context{}.uro_ifc_unit_uro_perfix xml_buffer, uro_ifc_int_building_installation_attribute{}.uro_ifc_project_uro_units_in_context{}.uro_ifc_unit_uro_name xml_buffer, uro_ifc_int_building_installation_attribute{}.uro_ifc_projected_crs_uro_name xml_buffer, uro_ifc_int_building_installation_attribute{}.uro_ifc_projected_crs_uro_description xml_buffer,
      uro_ifc_int_building_installation_attribute{}.uro_ifc_projected_crs_uro_geodetic_datum xml_buffer, uro_ifc_int_building_installation_attribute{}.uro_ifc_projected_crs_uro_vertical_datum xml_buffer, uro_ifc_int_building_installation_attribute{}.uro_ifc_projected_crs_uro_map_unit xml_buffer, uro_ifc_int_building_installation_attribute{}.uro_ifc_projected_crs_uro_map_projection xml_buffer, uro_ifc_int_building_installation_attribute{}.uro_ifc_projected_crs_uro_map_zone xml_buffer, uro_ifc_int_building_installation_attribute{}.uro_ifc_pset_building_common_uro_building_id xml_real64, uro_ifc_int_building_installation_attribute{}.uro_ifc_pset_building_common_uro_building_id_units xml_buffer, uro_ifc_int_building_installation_attribute{}.uro_ifc_pset_building_common_uro_is_permanent_id xml_real64, uro_ifc_int_building_installation_attribute{}.uro_ifc_pset_building_common_uro_is_permanent_id_units xml_buffer, uro_ifc_int_building_installation_attribute{}.uro_ifc_pset_building_common_uro_main_fire_use xml_buffer, uro_ifc_int_building_installation_attribute{}.uro_ifc_pset_building_common_uro_ancillary_fire_use xml_buffer, uro_ifc_int_building_installation_attribute{}.uro_ifc_pset_building_common_uro_sprinkler_protection xml_boolean, uro_ifc_int_building_installation_attribute{}.uro_ifc_pset_building_common_uro_sprinkler_protection_automatic xml_boolean, uro_ifc_int_building_installation_attribute{}.uro_ifc_pset_building_common_uro_occupancy_type xml_buffer, uro_ifc_int_building_installation_attribute{}.uro_ifc_pset_building_common_uro_occupancy_type_codeSpace xml_buffer, uro_ifc_int_building_installation_attribute{}.uro_ifc_pset_building_common_uro_gross_planned_area xml_real64, uro_ifc_int_building_installation_attribute{}.uro_ifc_pset_building_common_uro_gross_planned_area_units xml_buffer, uro_ifc_int_building_installation_attribute{}.uro_ifc_pset_building_common_uro_number_of_storeys xml_int64, uro_ifc_int_building_installation_attribute{}.uro_ifc_pset_building_common_uro_year_of_construction xml_buffer, uro_ifc_int_building_installation_attribute{}.uro_ifc_pset_building_common_uro_is_landmarked xml_boolean, uro_ifc_int_building_installation_attribute{}.uro_ifc_pset_door_common_uro_reference xml_buffer, uro_ifc_int_building_installation_attribute{}.uro_ifc_pset_door_common_uro_acoustic_rating xml_buffer, uro_ifc_int_building_installation_attribute{}.uro_ifc_pset_door_common_uro_firerating xml_buffer, uro_ifc_int_building_installation_attribute{}.uro_ifc_pset_door_common_uro_security_rating xml_buffer, uro_ifc_int_building_installation_attribute{}.uro_ifc_pset_door_common_uro_is_external xml_boolean, uro_ifc_int_building_installation_attribute{}.uro_ifc_pset_door_common_uro_infiltration xml_real64, uro_ifc_int_building_installation_attribute{}.uro_ifc_pset_door_common_uro_thermal_transmittance xml_real64, uro_ifc_int_building_installation_attribute{}.uro_ifc_pset_door_common_uro_glazing_area_fraction xml_real64, uro_ifc_int_building_installation_attribute{}.uro_ifc_pset_door_common_uro_handicap_accessible xml_real64, uro_ifc_int_building_installation_attribute{}.uro_ifc_pset_door_common_uro_fire_exit xml_boolean,
      uro_ifc_int_building_installation_attribute{}.uro_ifc_pset_door_common_uro_self_closing xml_real64, uro_ifc_int_building_installation_attribute{}.uro_ifc_pset_door_common_uro_smoke_stop xml_boolean, uro_ifc_int_building_installation_attribute{}.uro_ifc_pset_opening_element_common_uro_reference xml_buffer, uro_ifc_int_building_installation_attribute{}.uro_ifc_pset_opening_element_common_uro_purpose xml_buffer, uro_ifc_int_building_installation_attribute{}.uro_ifc_pset_opening_element_common_uro_fire_exit xml_boolean, uro_ifc_int_building_installation_attribute{}.uro_ifc_pset_opening_element_common_uro_protected_opening xml_boolean, uro_ifc_int_building_installation_attribute{}.uro_ifc_pset_opening_element_common_uro_parallel_jambs xml_boolean, uro_ifc_int_building_installation_attribute{}.uro_ifc_pset_site_common_uro_buildable_area xml_real64, uro_ifc_int_building_installation_attribute{}.uro_ifc_pset_site_common_uro_buildable_area_units xml_buffer, uro_ifc_int_building_installation_attribute{}.uro_ifc_pset_site_common_uro_total_area xml_real64, uro_ifc_int_building_installation_attribute{}.uro_ifc_pset_site_common_uro_total_area_units xml_buffer, uro_ifc_int_building_installation_attribute{}.uro_ifc_pset_site_common_uro_building_height_limit xml_real64, uro_ifc_int_building_installation_attribute{}.uro_ifc_pset_site_common_uro_building_height_limit_units xml_buffer, uro_ifc_int_building_installation_attribute{}.uro_ifc_pset_space_common_uro_reference xml_buffer, uro_ifc_int_building_installation_attribute{}.uro_ifc_pset_space_common_uro_category xml_buffer, uro_ifc_int_building_installation_attribute{}.uro_ifc_pset_space_common_uro_category_codeSpace xml_buffer, uro_ifc_int_building_installation_attribute{}.uro_ifc_pset_space_common_uro_floor_covering xml_buffer, uro_ifc_int_building_installation_attribute{}.uro_ifc_pset_space_common_uro_wall_covering xml_buffer, uro_ifc_int_building_installation_attribute{}.uro_ifc_pset_space_common_uro_ceiling_covering xml_buffer, uro_ifc_int_building_installation_attribute{}.uro_ifc_pset_space_common_uro_skirting_covering xml_buffer, uro_ifc_int_building_installation_attribute{}.uro_ifc_pset_space_common_uro_gross_planned_area xml_real64, uro_ifc_int_building_installation_attribute{}.uro_ifc_pset_space_common_uro_gross_planned_area_units xml_buffer, uro_ifc_int_building_installation_attribute{}.uro_ifc_pset_space_common_uro_net_planned_area xml_real64, uro_ifc_int_building_installation_attribute{}.uro_ifc_pset_space_common_uro_net_planned_area_units xml_buffer, uro_ifc_int_building_installation_attribute{}.uro_ifc_pset_space_common_uro_publicly_accessible xml_boolean, uro_ifc_int_building_installation_attribute{}.uro_ifc_pset_space_common_uro_handicap_accessible xml_boolean, uro_ifc_int_building_installation_attribute{}.uro_ifc_pset_space_common_uro_concealed_flooring xml_boolean, uro_ifc_int_building_installation_attribute{}.uro_ifc_pset_space_common_uro_concealed_ceiling xml_boolean, uro_ifc_int_building_installation_attribute{}.uro_ifc_pset_window_common_uro_reference xml_buffer, uro_ifc_int_building_installation_attribute{}.uro_ifc_pset_window_common_uro_acoustic_rating xml_buffer,
      uro_ifc_int_building_installation_attribute{}.uro_ifc_pset_window_common_uro_firerating xml_buffer, uro_ifc_int_building_installation_attribute{}.uro_ifc_pset_window_common_uro_security_rating xml_buffer, uro_ifc_int_building_installation_attribute{}.uro_ifc_pset_window_common_uro_is_external xml_boolean, uro_ifc_int_building_installation_attribute{}.uro_ifc_pset_window_common_uro_infiltration xml_real64, uro_ifc_int_building_installation_attribute{}.uro_ifc_pset_window_common_uro_thermal_transmittance xml_real64, uro_ifc_int_building_installation_attribute{}.uro_ifc_pset_window_common_uro_glazing_area_fraction xml_real64, uro_ifc_int_building_installation_attribute{}.uro_ifc_pset_window_common_uro_smoke_stop xml_boolean, uro_ifc_int_building_installation_attribute{}.uro_ifc_site_uro_global_id xml_buffer, uro_ifc_int_building_installation_attribute{}.uro_ifc_site_uro_name xml_buffer, uro_ifc_int_building_installation_attribute{}.uro_ifc_site_uro_description xml_buffer, uro_ifc_int_building_installation_attribute{}.uro_ifc_site_uro_object_type xml_buffer, uro_ifc_int_building_installation_attribute{}.uro_ifc_site_uro_long_name xml_buffer, uro_ifc_int_building_installation_attribute{}.uro_ifc_site_uro_composition_type xml_char(7), uro_ifc_int_building_installation_attribute{}.uro_ifc_site_uro_ref_longitude xml_real64, uro_ifc_int_building_installation_attribute{}.uro_ifc_site_uro_ref_latitude xml_real64, uro_ifc_int_building_installation_attribute{}.uro_ifc_site_uro_ref_elevation xml_real64, uro_ifc_int_building_installation_attribute{}.uro_ifc_site_uro_ref_elevation_units xml_buffer, uro_ifc_int_building_installation_attribute{}.uro_ifc_site_uro_land_title_number xml_buffer, uro_ifc_int_building_installation_attribute{}.uro_ifc_site_uro_site_address_xlink_href xml_buffer, uro_ifc_int_building_installation_attribute{}.uro_ifc_space_uro_global_id xml_buffer, uro_ifc_int_building_installation_attribute{}.uro_ifc_space_uro_name xml_buffer, uro_ifc_int_building_installation_attribute{}.uro_ifc_space_uro_description xml_buffer, uro_ifc_int_building_installation_attribute{}.uro_ifc_space_uro_object_type xml_buffer, uro_ifc_int_building_installation_attribute{}.uro_ifc_space_uro_long_name xml_buffer, uro_ifc_int_building_installation_attribute{}.uro_ifc_space_uro_composition_type xml_char(7), uro_ifc_int_building_installation_attribute{}.uro_ifc_space_uro_interioror_exterior_space xml_char(10), uro_ifc_int_building_installation_attribute{}.uro_ifc_space_uro_elevation_with_flooring xml_real64, uro_ifc_int_building_installation_attribute{}.uro_ifc_space_uro_elevation_with_flooring_units xml_buffer, uro_ifc_int_building_installation_attribute{}.uro_ifc_space_base_quantity_uro_nominal_height xml_real64, uro_ifc_int_building_installation_attribute{}.uro_ifc_space_base_quantity_uro_nominal_height_units xml_buffer,
      uro_ifc_int_building_installation_attribute{}.uro_ifc_space_base_quantity_uro_clear_height xml_real64, uro_ifc_int_building_installation_attribute{}.uro_ifc_space_base_quantity_uro_clear_height_units xml_buffer, uro_ifc_int_building_installation_attribute{}.uro_ifc_space_base_quantity_uro_finish_ceiling_height xml_real64, uro_ifc_int_building_installation_attribute{}.uro_ifc_space_base_quantity_uro_finish_ceiling_height_units xml_buffer, uro_ifc_int_building_installation_attribute{}.uro_ifc_space_base_quantity_uro_gross_perimeter xml_real64, uro_ifc_int_building_installation_attribute{}.uro_ifc_space_base_quantity_uro_gross_perimeter_units xml_buffer, uro_ifc_int_building_installation_attribute{}.uro_ifc_space_base_quantity_uro_net_perimeter xml_real64, uro_ifc_int_building_installation_attribute{}.uro_ifc_space_base_quantity_uro_net_perimeter_units xml_buffer, uro_ifc_int_building_installation_attribute{}.uro_ifc_space_base_quantity_uro_gross_ceiling_area xml_real64, uro_ifc_int_building_installation_attribute{}.uro_ifc_space_base_quantity_uro_gross_ceiling_area_units xml_buffer, uro_ifc_int_building_installation_attribute{}.uro_ifc_space_base_quantity_uro_gross_floor_area xml_real64, uro_ifc_int_building_installation_attribute{}.uro_ifc_space_base_quantity_uro_gross_floor_area_units xml_buffer, uro_ifc_int_building_installation_attribute{}.uro_ifc_space_base_quantity_uro_net_ceiling_area xml_real64, uro_ifc_int_building_installation_attribute{}.uro_ifc_space_base_quantity_uro_net_ceiling_area_units xml_buffer, uro_ifc_int_building_installation_attribute{}.uro_ifc_space_base_quantity_uro_net_floor_area xml_real64, uro_ifc_int_building_installation_attribute{}.uro_ifc_space_base_quantity_uro_net_floor_area_units xml_buffer, uro_ifc_int_building_installation_attribute{}.uro_ifc_space_base_quantity_uro_gross_wall_area xml_real64, uro_ifc_int_building_installation_attribute{}.uro_ifc_space_base_quantity_uro_gross_wall_area_units xml_buffer, uro_ifc_int_building_installation_attribute{}.uro_ifc_space_base_quantity_uro_net_wall_area xml_real64, uro_ifc_int_building_installation_attribute{}.uro_ifc_space_base_quantity_uro_net_wall_area_units xml_buffer, uro_ifc_int_building_installation_attribute{}.uro_ifc_space_base_quantity_uro_gross_volume xml_real64, uro_ifc_int_building_installation_attribute{}.uro_ifc_space_base_quantity_uro_gross_volume_units xml_buffer, uro_ifc_int_building_installation_attribute{}.uro_ifc_space_base_quantity_uro_net_volume xml_real64, uro_ifc_int_building_installation_attribute{}.uro_ifc_space_base_quantity_uro_net_volume_units xml_buffer, uro_ifc_int_building_installation_attribute{}.uro_ifc_wall_uro_global_id xml_buffer, uro_ifc_int_building_installation_attribute{}.uro_ifc_wall_uro_name xml_buffer, uro_ifc_int_building_installation_attribute{}.uro_ifc_wall_uro_description xml_buffer, uro_ifc_int_building_installation_attribute{}.uro_ifc_wall_uro_object_type xml_buffer, uro_ifc_int_building_installation_attribute{}.uro_ifc_wall_uro_tag xml_buffer, uro_ifc_int_building_installation_attribute{}.uro_ifc_wall_uro_element_type xml_buffer,
      uro_ifc_int_building_installation_attribute{}.uro_ifc_wall_uro_element_type_codeSpace xml_buffer, uro_ifc_int_building_installation_attribute{}.uro_ifc_wall_uro_predefined_type xml_buffer, uro_ifc_int_building_installation_attribute{}.uro_ifc_wall_uro_predefined_type_codeSpace xml_buffer, uro_ifc_int_building_installation_attribute{}.uro_ifc_wall_uro_shape_type xml_buffer, uro_ifc_int_building_installation_attribute{}.uro_ifc_wall_uro_shape_type_codeSpace xml_buffer, uro_ifc_int_building_installation_attribute{}.uro_ifc_wall_uro_number_of_riser xml_int64, uro_ifc_int_building_installation_attribute{}.uro_ifc_wall_uro_number_of_treads xml_int64, uro_ifc_int_building_installation_attribute{}.uro_ifc_wall_uro_riser_height xml_int64, uro_ifc_int_building_installation_attribute{}.uro_ifc_wall_uro_tread_length xml_int64, uro_ifc_int_building_installation_attribute{}.uro_ifc_wall_uro_operation_type xml_char(11), uro_ifc_int_building_installation_attribute{}.uro_ifc_wall_uro_capacity_by_weight xml_real64, uro_ifc_int_building_installation_attribute{}.uro_ifc_wall_uro_capacity_by_weight_units xml_buffer, uro_ifc_int_building_installation_attribute{}.uro_ifc_wall_uro_capacity_by_number xml_int64, uro_ifc_int_building_installation_attribute{}.uro_ifc_wall_uro_nominal_length xml_real64, uro_ifc_int_building_installation_attribute{}.uro_ifc_wall_uro_nominal_length_units xml_buffer, uro_ifc_int_building_installation_attribute{}.uro_ifc_wall_uro_nominal_width xml_real64, uro_ifc_int_building_installation_attribute{}.uro_ifc_wall_uro_nominal_width_units xml_buffer, uro_ifc_int_building_installation_attribute{}.uro_ifc_wall_uro_nominal_height xml_real64, uro_ifc_int_building_installation_attribute{}.uro_ifc_wall_uro_nominal_height_units xml_buffer, uro_ifc_int_building_installation_attribute{}.uro_ifc_wall_uro_gross_foot_print_area xml_real64, uro_ifc_int_building_installation_attribute{}.uro_ifc_wall_uro_gross_foot_print_area_units xml_buffer, uro_ifc_int_building_installation_attribute{}.uro_ifc_wall_uro_net_foot_print_area xml_real64, uro_ifc_int_building_installation_attribute{}.uro_ifc_wall_uro_net_foot_print_area_units xml_buffer, uro_ifc_int_building_installation_attribute{}.uro_ifc_wall_uro_gross_side_area xml_real64, uro_ifc_int_building_installation_attribute{}.uro_ifc_wall_uro_gross_side_area_units xml_buffer, uro_ifc_int_building_installation_attribute{}.uro_ifc_wall_uro_net_side_area xml_real64, uro_ifc_int_building_installation_attribute{}.uro_ifc_wall_uro_net_side_area_units xml_buffer, uro_ifc_int_building_installation_attribute{}.uro_ifc_wall_uro_gross_side_area_left xml_real64, uro_ifc_int_building_installation_attribute{}.uro_ifc_wall_uro_gross_side_area_left_units xml_buffer, uro_ifc_int_building_installation_attribute{}.uro_ifc_wall_uro_net_side_area_left xml_real64,
      uro_ifc_int_building_installation_attribute{}.uro_ifc_wall_uro_net_side_area_left_units xml_buffer, uro_ifc_int_building_installation_attribute{}.uro_ifc_wall_uro_gross_side_area_right xml_real64, uro_ifc_int_building_installation_attribute{}.uro_ifc_wall_uro_gross_side_area_right_units xml_buffer, uro_ifc_int_building_installation_attribute{}.uro_ifc_wall_uro_net_side_area_right xml_real64, uro_ifc_int_building_installation_attribute{}.uro_ifc_wall_uro_net_side_area_right_units xml_buffer, uro_ifc_int_building_installation_attribute{}.uro_ifc_wall_uro_gross_volume xml_real64, uro_ifc_int_building_installation_attribute{}.uro_ifc_wall_uro_gross_volume_units xml_buffer, uro_ifc_int_building_installation_attribute{}.uro_ifc_wall_uro_net_volume xml_real64, uro_ifc_int_building_installation_attribute{}.uro_ifc_wall_uro_net_volume_units xml_buffer, uro_ifc_int_building_installation_attribute{}.uro_ifc_wall_standard_case_uro_global_id xml_buffer, uro_ifc_int_building_installation_attribute{}.uro_ifc_wall_standard_case_uro_name xml_buffer, uro_ifc_int_building_installation_attribute{}.uro_ifc_wall_standard_case_uro_description xml_buffer, uro_ifc_int_building_installation_attribute{}.uro_ifc_wall_standard_case_uro_object_type xml_buffer, uro_ifc_int_building_installation_attribute{}.uro_ifc_wall_standard_case_uro_tag xml_buffer, uro_ifc_int_building_installation_attribute{}.uro_ifc_wall_standard_case_uro_element_type xml_buffer, uro_ifc_int_building_installation_attribute{}.uro_ifc_wall_standard_case_uro_element_type_codeSpace xml_buffer, uro_ifc_int_building_installation_attribute{}.uro_ifc_wall_standard_case_uro_predefined_type xml_buffer, uro_ifc_int_building_installation_attribute{}.uro_ifc_wall_standard_case_uro_predefined_type_codeSpace xml_buffer, uro_ifc_int_building_installation_attribute{}.uro_ifc_wall_standard_case_uro_shape_type xml_buffer, uro_ifc_int_building_installation_attribute{}.uro_ifc_wall_standard_case_uro_shape_type_codeSpace xml_buffer, uro_ifc_int_building_installation_attribute{}.uro_ifc_wall_standard_case_uro_number_of_riser xml_int64, uro_ifc_int_building_installation_attribute{}.uro_ifc_wall_standard_case_uro_number_of_treads xml_int64, uro_ifc_int_building_installation_attribute{}.uro_ifc_wall_standard_case_uro_riser_height xml_int64, uro_ifc_int_building_installation_attribute{}.uro_ifc_wall_standard_case_uro_tread_length xml_int64, uro_ifc_int_building_installation_attribute{}.uro_ifc_wall_standard_case_uro_operation_type xml_char(11), uro_ifc_int_building_installation_attribute{}.uro_ifc_wall_standard_case_uro_capacity_by_weight xml_real64, uro_ifc_int_building_installation_attribute{}.uro_ifc_wall_standard_case_uro_capacity_by_weight_units xml_buffer, uro_ifc_int_building_installation_attribute{}.uro_ifc_wall_standard_case_uro_capacity_by_number xml_int64, uro_ifc_int_building_installation_attribute{}.uro_ifc_wall_standard_case_uro_nominal_length xml_real64, uro_ifc_int_building_installation_attribute{}.uro_ifc_wall_standard_case_uro_nominal_length_units xml_buffer,
      uro_ifc_int_building_installation_attribute{}.uro_ifc_wall_standard_case_uro_nominal_width xml_real64, uro_ifc_int_building_installation_attribute{}.uro_ifc_wall_standard_case_uro_nominal_width_units xml_buffer, uro_ifc_int_building_installation_attribute{}.uro_ifc_wall_standard_case_uro_nominal_height xml_real64, uro_ifc_int_building_installation_attribute{}.uro_ifc_wall_standard_case_uro_nominal_height_units xml_buffer, uro_ifc_int_building_installation_attribute{}.uro_ifc_wall_standard_case_uro_gross_foot_print_area xml_real64, uro_ifc_int_building_installation_attribute{}.uro_ifc_wall_standard_case_uro_gross_foot_print_area_units xml_buffer, uro_ifc_int_building_installation_attribute{}.uro_ifc_wall_standard_case_uro_net_foot_print_area xml_real64, uro_ifc_int_building_installation_attribute{}.uro_ifc_wall_standard_case_uro_net_foot_print_area_units xml_buffer, uro_ifc_int_building_installation_attribute{}.uro_ifc_wall_standard_case_uro_gross_side_area xml_real64, uro_ifc_int_building_installation_attribute{}.uro_ifc_wall_standard_case_uro_gross_side_area_units xml_buffer, uro_ifc_int_building_installation_attribute{}.uro_ifc_wall_standard_case_uro_net_side_area xml_real64, uro_ifc_int_building_installation_attribute{}.uro_ifc_wall_standard_case_uro_net_side_area_units xml_buffer, uro_ifc_int_building_installation_attribute{}.uro_ifc_wall_standard_case_uro_gross_side_area_left xml_real64, uro_ifc_int_building_installation_attribute{}.uro_ifc_wall_standard_case_uro_gross_side_area_left_units xml_buffer, uro_ifc_int_building_installation_attribute{}.uro_ifc_wall_standard_case_uro_net_side_area_left xml_real64, uro_ifc_int_building_installation_attribute{}.uro_ifc_wall_standard_case_uro_net_side_area_left_units xml_buffer, uro_ifc_int_building_installation_attribute{}.uro_ifc_wall_standard_case_uro_gross_side_area_right xml_real64, uro_ifc_int_building_installation_attribute{}.uro_ifc_wall_standard_case_uro_gross_side_area_right_units xml_buffer, uro_ifc_int_building_installation_attribute{}.uro_ifc_wall_standard_case_uro_net_side_area_right xml_real64, uro_ifc_int_building_installation_attribute{}.uro_ifc_wall_standard_case_uro_net_side_area_right_units xml_buffer, uro_ifc_int_building_installation_attribute{}.uro_ifc_wall_standard_case_uro_gross_volume xml_real64, uro_ifc_int_building_installation_attribute{}.uro_ifc_wall_standard_case_uro_gross_volume_units xml_buffer, uro_ifc_int_building_installation_attribute{}.uro_ifc_wall_standard_case_uro_net_volume xml_real64, uro_ifc_int_building_installation_attribute{}.uro_ifc_wall_standard_case_uro_net_volume_units xml_buffer, uro_ifc_int_building_installation_attribute{}.uro_ifc_window_uro_global_id xml_buffer, uro_ifc_int_building_installation_attribute{}.uro_ifc_window_uro_name xml_buffer, uro_ifc_int_building_installation_attribute{}.uro_ifc_window_uro_description xml_buffer, uro_ifc_int_building_installation_attribute{}.uro_ifc_window_uro_object_type xml_buffer, uro_ifc_int_building_installation_attribute{}.uro_ifc_window_uro_tag xml_buffer, uro_ifc_int_building_installation_attribute{}.uro_ifc_window_uro_element_type xml_buffer,
      uro_ifc_int_building_installation_attribute{}.uro_ifc_window_uro_element_type_codeSpace xml_buffer, uro_ifc_int_building_installation_attribute{}.uro_ifc_window_uro_predefined_type xml_buffer, uro_ifc_int_building_installation_attribute{}.uro_ifc_window_uro_predefined_type_codeSpace xml_buffer, uro_ifc_int_building_installation_attribute{}.uro_ifc_window_uro_shape_type xml_buffer, uro_ifc_int_building_installation_attribute{}.uro_ifc_window_uro_shape_type_codeSpace xml_buffer, uro_ifc_int_building_installation_attribute{}.uro_ifc_window_uro_number_of_riser xml_int64, uro_ifc_int_building_installation_attribute{}.uro_ifc_window_uro_number_of_treads xml_int64, uro_ifc_int_building_installation_attribute{}.uro_ifc_window_uro_riser_height xml_int64, uro_ifc_int_building_installation_attribute{}.uro_ifc_window_uro_tread_length xml_int64, uro_ifc_int_building_installation_attribute{}.uro_ifc_window_uro_operation_type xml_char(11), uro_ifc_int_building_installation_attribute{}.uro_ifc_window_uro_capacity_by_weight xml_real64, uro_ifc_int_building_installation_attribute{}.uro_ifc_window_uro_capacity_by_weight_units xml_buffer, uro_ifc_int_building_installation_attribute{}.uro_ifc_window_uro_capacity_by_number xml_int64, uro_ifc_int_building_installation_attribute{}.uro_ifc_window_uro_overall_height xml_real64, uro_ifc_int_building_installation_attribute{}.uro_ifc_window_uro_overall_height_units xml_buffer, uro_ifc_int_building_installation_attribute{}.uro_ifc_window_uro_overall_width xml_real64, uro_ifc_int_building_installation_attribute{}.uro_ifc_window_uro_overall_width_units xml_buffer
GeometryReplacer_5
    KIND_LONG = FME Binary
    REMOVE_ATTRIBUTE = Yes
    SOURCE = @Value(_geometry)
    -> AttributeCreator_16
AttributeCreator_16
    ATTR_TABLE:
      SET_TO gml_id = inst_@UUID()
      SET_TO gml_parent_id = @Value(_building_id)
      SET_TO citygml_lod_name = lod4Geometry
      SET_TO citygml_feature_role = outerBuildingInstallation
      SET_TO _citygml_feature_type = BuildingInstallation
    -> GeometryPropertySetter_10
GeometryPropertySetter_10
    GQUERY:
      for $geom in //geometry
      where $geom/count(parent::geometry) = 0
      return number($geom/@fme_id)
    OVERWRITE_CHOICE = Yes
    REMOVE_ATTRIBUTE = No
    SETTYPE_PARAM = Traits From Attributes
    SRC_ATTRS = citygml_lod_name
    SET -> PLATEAU.IfcReprojector_3 [IfcFeature]
PLATEAU.IfcReprojector_3
    DEST_COORDSYS = $(DEST_COORDSYS)
    LENGTH_MULTIPLIER = @Value(_lengthmultiplier)
    REPROJECTION_PARAMS = @Value(_reprojection_params)
    Reprojected -> BuildingInstallation (writer CITYGML_2)
BuildingInstallation (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer, uro_ifc_building_installation_attribute{}.uro_ifc_building_uro_global_id xml_buffer, uro_ifc_building_installation_attribute{}.uro_ifc_building_uro_name xml_buffer, uro_ifc_building_installation_attribute{}.uro_ifc_building_uro_description xml_buffer, uro_ifc_building_installation_attribute{}.uro_ifc_building_uro_object_type xml_buffer, uro_ifc_building_installation_attribute{}.uro_ifc_building_uro_long_name xml_buffer, uro_ifc_building_installation_attribute{}.uro_ifc_building_uro_composition_type xml_char(7), uro_ifc_building_installation_attribute{}.uro_ifc_building_uro_elevation_of_ref_height xml_real64, uro_ifc_building_installation_attribute{}.uro_ifc_building_uro_elevation_of_ref_height_units xml_buffer,
      uro_ifc_building_installation_attribute{}.uro_ifc_building_uro_elevation_of_terrain xml_real64, uro_ifc_building_installation_attribute{}.uro_ifc_building_uro_elevation_of_terrain_units xml_buffer, uro_ifc_building_installation_attribute{}.uro_ifc_building_uro_building_address_xlink_href xml_buffer, uro_ifc_building_installation_attribute{}.uro_ifc_building_element_uro_global_id xml_buffer, uro_ifc_building_installation_attribute{}.uro_ifc_building_element_uro_name xml_buffer, uro_ifc_building_installation_attribute{}.uro_ifc_building_element_uro_description xml_buffer, uro_ifc_building_installation_attribute{}.uro_ifc_building_element_uro_object_type xml_buffer, uro_ifc_building_installation_attribute{}.uro_ifc_building_element_uro_tag xml_buffer, uro_ifc_building_installation_attribute{}.uro_ifc_building_element_uro_element_type xml_buffer, uro_ifc_building_installation_attribute{}.uro_ifc_building_element_uro_element_type_codeSpace xml_buffer, uro_ifc_building_installation_attribute{}.uro_ifc_building_element_uro_predefined_type xml_buffer, uro_ifc_building_installation_attribute{}.uro_ifc_building_element_uro_predefined_type_codeSpace xml_buffer, uro_ifc_building_installation_attribute{}.uro_ifc_building_element_uro_shape_type xml_buffer, uro_ifc_building_installation_attribute{}.uro_ifc_building_element_uro_shape_type_codeSpace xml_buffer, uro_ifc_building_installation_attribute{}.uro_ifc_building_element_uro_number_of_riser xml_int64, uro_ifc_building_installation_attribute{}.uro_ifc_building_element_uro_number_of_treads xml_int64, uro_ifc_building_installation_attribute{}.uro_ifc_building_element_uro_riser_height xml_int64, uro_ifc_building_installation_attribute{}.uro_ifc_building_element_uro_tread_length xml_int64, uro_ifc_building_installation_attribute{}.uro_ifc_building_element_uro_operation_type xml_char(11), uro_ifc_building_installation_attribute{}.uro_ifc_building_element_uro_capacity_by_weight xml_real64, uro_ifc_building_installation_attribute{}.uro_ifc_building_element_uro_capacity_by_weight_units xml_buffer, uro_ifc_building_installation_attribute{}.uro_ifc_building_element_uro_capacity_by_number xml_int64, uro_ifc_building_installation_attribute{}.uro_ifc_building_storey_uro_global_id xml_buffer, uro_ifc_building_installation_attribute{}.uro_ifc_building_storey_uro_name xml_buffer, uro_ifc_building_installation_attribute{}.uro_ifc_building_storey_uro_description xml_buffer, uro_ifc_building_installation_attribute{}.uro_ifc_building_storey_uro_object_type xml_buffer, uro_ifc_building_installation_attribute{}.uro_ifc_building_storey_uro_long_name xml_buffer, uro_ifc_building_installation_attribute{}.uro_ifc_building_storey_uro_composition_type xml_char(7), uro_ifc_building_installation_attribute{}.uro_ifc_building_storey_uro_elevation xml_real64, uro_ifc_building_installation_attribute{}.uro_ifc_building_storey_uro_elevation_units xml_buffer,
      uro_ifc_building_installation_attribute{}.uro_ifc_classification_reference_uro_location xml_buffer, uro_ifc_building_installation_attribute{}.uro_ifc_classification_reference_uro_item_reference xml_buffer, uro_ifc_building_installation_attribute{}.uro_ifc_classification_reference_uro_item_reference_codeSpace xml_buffer, uro_ifc_building_installation_attribute{}.uro_ifc_classification_reference_uro_name xml_buffer, uro_ifc_building_installation_attribute{}.uro_ifc_classification_reference_uro_name_codeSpace xml_buffer, uro_ifc_building_installation_attribute{}.uro_ifc_classification_reference_uro_reference_source_uro_ifc_classification_uro_source xml_buffer, uro_ifc_building_installation_attribute{}.uro_ifc_classification_reference_uro_reference_source_uro_ifc_classification_uro_edition xml_buffer, uro_ifc_building_installation_attribute{}.uro_ifc_classification_reference_uro_reference_source_uro_ifc_classification_uro_edition_date xml_date, uro_ifc_building_installation_attribute{}.uro_ifc_classification_reference_uro_reference_source_uro_ifc_classification_uro_name xml_buffer, uro_ifc_building_installation_attribute{}.uro_ifc_coordinate_reference_system_uro_name xml_buffer, uro_ifc_building_installation_attribute{}.uro_ifc_coordinate_reference_system_uro_description xml_buffer, uro_ifc_building_installation_attribute{}.uro_ifc_coordinate_reference_system_uro_geodetic_datum xml_buffer, uro_ifc_building_installation_attribute{}.uro_ifc_coordinate_reference_system_uro_vertical_datum xml_buffer, uro_ifc_building_installation_attribute{}.uro_ifc_curtain_wall_uro_global_id xml_buffer, uro_ifc_building_installation_attribute{}.uro_ifc_curtain_wall_uro_name xml_buffer, uro_ifc_building_installation_attribute{}.uro_ifc_curtain_wall_uro_description xml_buffer, uro_ifc_building_installation_attribute{}.uro_ifc_curtain_wall_uro_object_type xml_buffer, uro_ifc_building_installation_attribute{}.uro_ifc_curtain_wall_uro_tag xml_buffer, uro_ifc_building_installation_attribute{}.uro_ifc_curtain_wall_uro_element_type xml_buffer, uro_ifc_building_installation_attribute{}.uro_ifc_curtain_wall_uro_element_type_codeSpace xml_buffer, uro_ifc_building_installation_attribute{}.uro_ifc_curtain_wall_uro_predefined_type xml_buffer, uro_ifc_building_installation_attribute{}.uro_ifc_curtain_wall_uro_predefined_type_codeSpace xml_buffer, uro_ifc_building_installation_attribute{}.uro_ifc_curtain_wall_uro_shape_type xml_buffer, uro_ifc_building_installation_attribute{}.uro_ifc_curtain_wall_uro_shape_type_codeSpace xml_buffer, uro_ifc_building_installation_attribute{}.uro_ifc_curtain_wall_uro_number_of_riser xml_int64, uro_ifc_building_installation_attribute{}.uro_ifc_curtain_wall_uro_number_of_treads xml_int64, uro_ifc_building_installation_attribute{}.uro_ifc_curtain_wall_uro_riser_height xml_int64, uro_ifc_building_installation_attribute{}.uro_ifc_curtain_wall_uro_tread_length xml_int64, uro_ifc_building_installation_attribute{}.uro_ifc_curtain_wall_uro_operation_type xml_char(11), uro_ifc_building_installation_attribute{}.uro_ifc_curtain_wall_uro_capacity_by_weight xml_real64,
      uro_ifc_building_installation_attribute{}.uro_ifc_curtain_wall_uro_capacity_by_weight_units xml_buffer, uro_ifc_building_installation_attribute{}.uro_ifc_curtain_wall_uro_capacity_by_number xml_int64, uro_ifc_building_installation_attribute{}.uro_ifc_door_uro_global_id xml_buffer, uro_ifc_building_installation_attribute{}.uro_ifc_door_uro_name xml_buffer, uro_ifc_building_installation_attribute{}.uro_ifc_door_uro_description xml_buffer, uro_ifc_building_installation_attribute{}.uro_ifc_door_uro_object_type xml_buffer, uro_ifc_building_installation_attribute{}.uro_ifc_door_uro_tag xml_buffer, uro_ifc_building_installation_attribute{}.uro_ifc_door_uro_element_type xml_buffer, uro_ifc_building_installation_attribute{}.uro_ifc_door_uro_element_type_codeSpace xml_buffer, uro_ifc_building_installation_attribute{}.uro_ifc_door_uro_predefined_type xml_buffer, uro_ifc_building_installation_attribute{}.uro_ifc_door_uro_predefined_type_codeSpace xml_buffer, uro_ifc_building_installation_attribute{}.uro_ifc_door_uro_shape_type xml_buffer, uro_ifc_building_installation_attribute{}.uro_ifc_door_uro_shape_type_codeSpace xml_buffer, uro_ifc_building_installation_attribute{}.uro_ifc_door_uro_number_of_riser xml_int64, uro_ifc_building_installation_attribute{}.uro_ifc_door_uro_number_of_treads xml_int64, uro_ifc_building_installation_attribute{}.uro_ifc_door_uro_riser_height xml_int64, uro_ifc_building_installation_attribute{}.uro_ifc_door_uro_tread_length xml_int64, uro_ifc_building_installation_attribute{}.uro_ifc_door_uro_operation_type xml_char(11), uro_ifc_building_installation_attribute{}.uro_ifc_door_uro_capacity_by_weight xml_real64, uro_ifc_building_installation_attribute{}.uro_ifc_door_uro_capacity_by_weight_units xml_buffer, uro_ifc_building_installation_attribute{}.uro_ifc_door_uro_capacity_by_number xml_int64, uro_ifc_building_installation_attribute{}.uro_ifc_door_uro_overall_height xml_real64, uro_ifc_building_installation_attribute{}.uro_ifc_door_uro_overall_height_units xml_buffer, uro_ifc_building_installation_attribute{}.uro_ifc_door_uro_overall_width xml_real64, uro_ifc_building_installation_attribute{}.uro_ifc_door_uro_overall_width_units xml_buffer, uro_ifc_building_installation_attribute{}.uro_ifc_furnishing_element_uro_global_id xml_buffer, uro_ifc_building_installation_attribute{}.uro_ifc_furnishing_element_uro_name xml_buffer, uro_ifc_building_installation_attribute{}.uro_ifc_furnishing_element_uro_description xml_buffer, uro_ifc_building_installation_attribute{}.uro_ifc_furnishing_element_uro_object_type xml_buffer, uro_ifc_building_installation_attribute{}.uro_ifc_furnishing_element_uro_tag xml_buffer,
      uro_ifc_building_installation_attribute{}.uro_ifc_map_conversion_uro_source_crs_uro_crs_uro_ifc_projected_crs_uro_name xml_buffer, uro_ifc_building_installation_attribute{}.uro_ifc_map_conversion_uro_source_crs_uro_crs_uro_ifc_projected_crs_uro_description xml_buffer, uro_ifc_building_installation_attribute{}.uro_ifc_map_conversion_uro_source_crs_uro_crs_uro_ifc_projected_crs_uro_geodetic_datum xml_buffer, uro_ifc_building_installation_attribute{}.uro_ifc_map_conversion_uro_source_crs_uro_crs_uro_ifc_projected_crs_uro_vertical_datum xml_buffer, uro_ifc_building_installation_attribute{}.uro_ifc_map_conversion_uro_source_crs_uro_crs_uro_ifc_projected_crs_uro_map_unit xml_buffer, uro_ifc_building_installation_attribute{}.uro_ifc_map_conversion_uro_source_crs_uro_crs_uro_ifc_projected_crs_uro_map_projection xml_buffer, uro_ifc_building_installation_attribute{}.uro_ifc_map_conversion_uro_source_crs_uro_crs_uro_ifc_projected_crs_uro_map_zone xml_buffer, uro_ifc_building_installation_attribute{}.uro_ifc_map_conversion_uro_source_crs_uro_crs_uro_ifc_coordinate_reference_system_uro_name xml_buffer, uro_ifc_building_installation_attribute{}.uro_ifc_map_conversion_uro_source_crs_uro_crs_uro_ifc_coordinate_reference_system_uro_description xml_buffer, uro_ifc_building_installation_attribute{}.uro_ifc_map_conversion_uro_source_crs_uro_crs_uro_ifc_coordinate_reference_system_uro_geodetic_datum xml_buffer, uro_ifc_building_installation_attribute{}.uro_ifc_map_conversion_uro_source_crs_uro_crs_uro_ifc_coordinate_reference_system_uro_vertical_datum xml_buffer, uro_ifc_building_installation_attribute{}.uro_ifc_map_conversion_uro_source_crs_uro_context_uro_ifc_geometric_representation_context_uro_context_identifier xml_buffer, uro_ifc_building_installation_attribute{}.uro_ifc_map_conversion_uro_source_crs_uro_context_uro_ifc_geometric_representation_context_uro_context_type xml_buffer, uro_ifc_building_installation_attribute{}.uro_ifc_map_conversion_uro_source_crs_uro_context_uro_ifc_geometric_representation_context_uro_coordinate_space_dimension xml_int64, uro_ifc_building_installation_attribute{}.uro_ifc_map_conversion_uro_source_crs_uro_context_uro_ifc_geometric_representation_context_uro_precision xml_real64, uro_ifc_building_installation_attribute{}.uro_ifc_map_conversion_uro_source_crs_uro_context_uro_ifc_geometric_representation_context_uro_true_north xml_real64, uro_ifc_building_installation_attribute{}.uro_ifc_map_conversion_uro_target_crs_uro_ifc_projected_crs_uro_name xml_buffer, uro_ifc_building_installation_attribute{}.uro_ifc_map_conversion_uro_target_crs_uro_ifc_projected_crs_uro_description xml_buffer, uro_ifc_building_installation_attribute{}.uro_ifc_map_conversion_uro_target_crs_uro_ifc_projected_crs_uro_geodetic_datum xml_buffer, uro_ifc_building_installation_attribute{}.uro_ifc_map_conversion_uro_target_crs_uro_ifc_projected_crs_uro_vertical_datum xml_buffer, uro_ifc_building_installation_attribute{}.uro_ifc_map_conversion_uro_target_crs_uro_ifc_projected_crs_uro_map_unit xml_buffer, uro_ifc_building_installation_attribute{}.uro_ifc_map_conversion_uro_target_crs_uro_ifc_projected_crs_uro_map_projection xml_buffer, uro_ifc_building_installation_attribute{}.uro_ifc_map_conversion_uro_target_crs_uro_ifc_projected_crs_uro_map_zone xml_buffer, uro_ifc_building_installation_attribute{}.uro_ifc_map_conversion_uro_target_crs_uro_ifc_coordinate_reference_system_uro_name xml_buffer, uro_ifc_building_installation_attribute{}.uro_ifc_map_conversion_uro_target_crs_uro_ifc_coordinate_reference_system_uro_description xml_buffer, uro_ifc_building_installation_attribute{}.uro_ifc_map_conversion_uro_target_crs_uro_ifc_coordinate_reference_system_uro_geodetic_datum xml_buffer, uro_ifc_building_installation_attribute{}.uro_ifc_map_conversion_uro_target_crs_uro_ifc_coordinate_reference_system_uro_vertical_datum xml_buffer, uro_ifc_building_installation_attribute{}.uro_ifc_map_conversion_uro_eastings xml_buffer, uro_ifc_building_installation_attribute{}.uro_ifc_map_conversion_uro_northings xml_buffer, uro_ifc_building_installation_attribute{}.uro_ifc_map_conversion_uro_orthogonal_height xml_real64,
      uro_ifc_building_installation_attribute{}.uro_ifc_map_conversion_uro_orthogonal_height_units xml_buffer, uro_ifc_building_installation_attribute{}.uro_ifc_map_conversion_uro_x_axis_abscissa xml_real64, uro_ifc_building_installation_attribute{}.uro_ifc_map_conversion_uro_x_axis_ordinate xml_real64, uro_ifc_building_installation_attribute{}.uro_ifc_map_conversion_uro_scale xml_real64, uro_ifc_building_installation_attribute{}.uro_ifc_opening_element_uro_global_id xml_buffer, uro_ifc_building_installation_attribute{}.uro_ifc_opening_element_uro_name xml_buffer, uro_ifc_building_installation_attribute{}.uro_ifc_opening_element_uro_description xml_buffer, uro_ifc_building_installation_attribute{}.uro_ifc_opening_element_uro_object_type xml_buffer, uro_ifc_building_installation_attribute{}.uro_ifc_opening_element_uro_tag xml_buffer, uro_ifc_building_installation_attribute{}.uro_ifc_opening_element_uro_nominal_area xml_real64, uro_ifc_building_installation_attribute{}.uro_ifc_opening_element_uro_nominal_area_units xml_buffer, uro_ifc_building_installation_attribute{}.uro_ifc_opening_element_uro_nominal_volume xml_real64, uro_ifc_building_installation_attribute{}.uro_ifc_opening_element_uro_nominal_volume_units xml_buffer, uro_ifc_building_installation_attribute{}.uro_ifc_project_uro_global_id xml_buffer, uro_ifc_building_installation_attribute{}.uro_ifc_project_uro_name xml_buffer, uro_ifc_building_installation_attribute{}.uro_ifc_project_uro_description xml_buffer, uro_ifc_building_installation_attribute{}.uro_ifc_project_uro_object_type xml_buffer, uro_ifc_building_installation_attribute{}.uro_ifc_project_uro_long_name xml_buffer, uro_ifc_building_installation_attribute{}.uro_ifc_project_uro_phase xml_buffer, uro_ifc_building_installation_attribute{}.uro_ifc_project_uro_representation_contexts_uro_ifc_geometric_representation_context_uro_context_identifier xml_buffer, uro_ifc_building_installation_attribute{}.uro_ifc_project_uro_representation_contexts_uro_ifc_geometric_representation_context_uro_context_type xml_buffer, uro_ifc_building_installation_attribute{}.uro_ifc_project_uro_representation_contexts_uro_ifc_geometric_representation_context_uro_coordinate_space_dimension xml_int64, uro_ifc_building_installation_attribute{}.uro_ifc_project_uro_representation_contexts_uro_ifc_geometric_representation_context_uro_precision xml_real64, uro_ifc_building_installation_attribute{}.uro_ifc_project_uro_representation_contexts_uro_ifc_geometric_representation_context_uro_true_north xml_real64, uro_ifc_building_installation_attribute{}.uro_ifc_project_uro_units_in_context{}.uro_ifc_unit_uro_dimensions xml_int64, uro_ifc_building_installation_attribute{}.uro_ifc_project_uro_units_in_context{}.uro_ifc_unit_uro_unit_type xml_char(28), uro_ifc_building_installation_attribute{}.uro_ifc_project_uro_units_in_context{}.uro_ifc_unit_uro_perfix xml_buffer, uro_ifc_building_installation_attribute{}.uro_ifc_project_uro_units_in_context{}.uro_ifc_unit_uro_name xml_buffer, uro_ifc_building_installation_attribute{}.uro_ifc_projected_crs_uro_name xml_buffer, uro_ifc_building_installation_attribute{}.uro_ifc_projected_crs_uro_description xml_buffer,
      uro_ifc_building_installation_attribute{}.uro_ifc_projected_crs_uro_geodetic_datum xml_buffer, uro_ifc_building_installation_attribute{}.uro_ifc_projected_crs_uro_vertical_datum xml_buffer, uro_ifc_building_installation_attribute{}.uro_ifc_projected_crs_uro_map_unit xml_buffer, uro_ifc_building_installation_attribute{}.uro_ifc_projected_crs_uro_map_projection xml_buffer, uro_ifc_building_installation_attribute{}.uro_ifc_projected_crs_uro_map_zone xml_buffer, uro_ifc_building_installation_attribute{}.uro_ifc_pset_building_common_uro_building_id xml_real64, uro_ifc_building_installation_attribute{}.uro_ifc_pset_building_common_uro_building_id_units xml_buffer, uro_ifc_building_installation_attribute{}.uro_ifc_pset_building_common_uro_is_permanent_id xml_real64, uro_ifc_building_installation_attribute{}.uro_ifc_pset_building_common_uro_is_permanent_id_units xml_buffer, uro_ifc_building_installation_attribute{}.uro_ifc_pset_building_common_uro_main_fire_use xml_buffer, uro_ifc_building_installation_attribute{}.uro_ifc_pset_building_common_uro_ancillary_fire_use xml_buffer, uro_ifc_building_installation_attribute{}.uro_ifc_pset_building_common_uro_sprinkler_protection xml_boolean, uro_ifc_building_installation_attribute{}.uro_ifc_pset_building_common_uro_sprinkler_protection_automatic xml_boolean, uro_ifc_building_installation_attribute{}.uro_ifc_pset_building_common_uro_occupancy_type xml_buffer, uro_ifc_building_installation_attribute{}.uro_ifc_pset_building_common_uro_occupancy_type_codeSpace xml_buffer, uro_ifc_building_installation_attribute{}.uro_ifc_pset_building_common_uro_gross_planned_area xml_real64, uro_ifc_building_installation_attribute{}.uro_ifc_pset_building_common_uro_gross_planned_area_units xml_buffer, uro_ifc_building_installation_attribute{}.uro_ifc_pset_building_common_uro_number_of_storeys xml_int64, uro_ifc_building_installation_attribute{}.uro_ifc_pset_building_common_uro_year_of_construction xml_buffer, uro_ifc_building_installation_attribute{}.uro_ifc_pset_building_common_uro_is_landmarked xml_boolean, uro_ifc_building_installation_attribute{}.uro_ifc_pset_door_common_uro_reference xml_buffer, uro_ifc_building_installation_attribute{}.uro_ifc_pset_door_common_uro_acoustic_rating xml_buffer, uro_ifc_building_installation_attribute{}.uro_ifc_pset_door_common_uro_firerating xml_buffer, uro_ifc_building_installation_attribute{}.uro_ifc_pset_door_common_uro_security_rating xml_buffer, uro_ifc_building_installation_attribute{}.uro_ifc_pset_door_common_uro_is_external xml_boolean, uro_ifc_building_installation_attribute{}.uro_ifc_pset_door_common_uro_infiltration xml_real64, uro_ifc_building_installation_attribute{}.uro_ifc_pset_door_common_uro_thermal_transmittance xml_real64, uro_ifc_building_installation_attribute{}.uro_ifc_pset_door_common_uro_glazing_area_fraction xml_real64, uro_ifc_building_installation_attribute{}.uro_ifc_pset_door_common_uro_handicap_accessible xml_real64, uro_ifc_building_installation_attribute{}.uro_ifc_pset_door_common_uro_fire_exit xml_boolean,
      uro_ifc_building_installation_attribute{}.uro_ifc_pset_door_common_uro_self_closing xml_real64, uro_ifc_building_installation_attribute{}.uro_ifc_pset_door_common_uro_smoke_stop xml_boolean, uro_ifc_building_installation_attribute{}.uro_ifc_pset_opening_element_common_uro_reference xml_buffer, uro_ifc_building_installation_attribute{}.uro_ifc_pset_opening_element_common_uro_purpose xml_buffer, uro_ifc_building_installation_attribute{}.uro_ifc_pset_opening_element_common_uro_fire_exit xml_boolean, uro_ifc_building_installation_attribute{}.uro_ifc_pset_opening_element_common_uro_protected_opening xml_boolean, uro_ifc_building_installation_attribute{}.uro_ifc_pset_opening_element_common_uro_parallel_jambs xml_boolean, uro_ifc_building_installation_attribute{}.uro_ifc_pset_site_common_uro_buildable_area xml_real64, uro_ifc_building_installation_attribute{}.uro_ifc_pset_site_common_uro_buildable_area_units xml_buffer, uro_ifc_building_installation_attribute{}.uro_ifc_pset_site_common_uro_total_area xml_real64, uro_ifc_building_installation_attribute{}.uro_ifc_pset_site_common_uro_total_area_units xml_buffer, uro_ifc_building_installation_attribute{}.uro_ifc_pset_site_common_uro_building_height_limit xml_real64, uro_ifc_building_installation_attribute{}.uro_ifc_pset_site_common_uro_building_height_limit_units xml_buffer, uro_ifc_building_installation_attribute{}.uro_ifc_pset_space_common_uro_reference xml_buffer, uro_ifc_building_installation_attribute{}.uro_ifc_pset_space_common_uro_category xml_buffer, uro_ifc_building_installation_attribute{}.uro_ifc_pset_space_common_uro_category_codeSpace xml_buffer, uro_ifc_building_installation_attribute{}.uro_ifc_pset_space_common_uro_floor_covering xml_buffer, uro_ifc_building_installation_attribute{}.uro_ifc_pset_space_common_uro_wall_covering xml_buffer, uro_ifc_building_installation_attribute{}.uro_ifc_pset_space_common_uro_ceiling_covering xml_buffer, uro_ifc_building_installation_attribute{}.uro_ifc_pset_space_common_uro_skirting_covering xml_buffer, uro_ifc_building_installation_attribute{}.uro_ifc_pset_space_common_uro_gross_planned_area xml_real64, uro_ifc_building_installation_attribute{}.uro_ifc_pset_space_common_uro_gross_planned_area_units xml_buffer, uro_ifc_building_installation_attribute{}.uro_ifc_pset_space_common_uro_net_planned_area xml_real64, uro_ifc_building_installation_attribute{}.uro_ifc_pset_space_common_uro_net_planned_area_units xml_buffer, uro_ifc_building_installation_attribute{}.uro_ifc_pset_space_common_uro_publicly_accessible xml_boolean, uro_ifc_building_installation_attribute{}.uro_ifc_pset_space_common_uro_handicap_accessible xml_boolean, uro_ifc_building_installation_attribute{}.uro_ifc_pset_space_common_uro_concealed_flooring xml_boolean, uro_ifc_building_installation_attribute{}.uro_ifc_pset_space_common_uro_concealed_ceiling xml_boolean, uro_ifc_building_installation_attribute{}.uro_ifc_pset_window_common_uro_reference xml_buffer, uro_ifc_building_installation_attribute{}.uro_ifc_pset_window_common_uro_acoustic_rating xml_buffer,
      uro_ifc_building_installation_attribute{}.uro_ifc_pset_window_common_uro_firerating xml_buffer, uro_ifc_building_installation_attribute{}.uro_ifc_pset_window_common_uro_security_rating xml_buffer, uro_ifc_building_installation_attribute{}.uro_ifc_pset_window_common_uro_is_external xml_boolean, uro_ifc_building_installation_attribute{}.uro_ifc_pset_window_common_uro_infiltration xml_real64, uro_ifc_building_installation_attribute{}.uro_ifc_pset_window_common_uro_thermal_transmittance xml_real64, uro_ifc_building_installation_attribute{}.uro_ifc_pset_window_common_uro_glazing_area_fraction xml_real64, uro_ifc_building_installation_attribute{}.uro_ifc_pset_window_common_uro_smoke_stop xml_boolean, uro_ifc_building_installation_attribute{}.uro_ifc_site_uro_global_id xml_buffer, uro_ifc_building_installation_attribute{}.uro_ifc_site_uro_name xml_buffer, uro_ifc_building_installation_attribute{}.uro_ifc_site_uro_description xml_buffer, uro_ifc_building_installation_attribute{}.uro_ifc_site_uro_object_type xml_buffer, uro_ifc_building_installation_attribute{}.uro_ifc_site_uro_long_name xml_buffer, uro_ifc_building_installation_attribute{}.uro_ifc_site_uro_composition_type xml_char(7), uro_ifc_building_installation_attribute{}.uro_ifc_site_uro_ref_longitude xml_real64, uro_ifc_building_installation_attribute{}.uro_ifc_site_uro_ref_latitude xml_real64, uro_ifc_building_installation_attribute{}.uro_ifc_site_uro_ref_elevation xml_real64, uro_ifc_building_installation_attribute{}.uro_ifc_site_uro_ref_elevation_units xml_buffer, uro_ifc_building_installation_attribute{}.uro_ifc_site_uro_land_title_number xml_buffer, uro_ifc_building_installation_attribute{}.uro_ifc_site_uro_site_address_xlink_href xml_buffer, uro_ifc_building_installation_attribute{}.uro_ifc_space_uro_global_id xml_buffer, uro_ifc_building_installation_attribute{}.uro_ifc_space_uro_name xml_buffer, uro_ifc_building_installation_attribute{}.uro_ifc_space_uro_description xml_buffer, uro_ifc_building_installation_attribute{}.uro_ifc_space_uro_object_type xml_buffer, uro_ifc_building_installation_attribute{}.uro_ifc_space_uro_long_name xml_buffer, uro_ifc_building_installation_attribute{}.uro_ifc_space_uro_composition_type xml_char(7), uro_ifc_building_installation_attribute{}.uro_ifc_space_uro_interioror_exterior_space xml_char(10), uro_ifc_building_installation_attribute{}.uro_ifc_space_uro_elevation_with_flooring xml_real64, uro_ifc_building_installation_attribute{}.uro_ifc_space_uro_elevation_with_flooring_units xml_buffer, uro_ifc_building_installation_attribute{}.uro_ifc_space_base_quantity_uro_nominal_height xml_real64, uro_ifc_building_installation_attribute{}.uro_ifc_space_base_quantity_uro_nominal_height_units xml_buffer,
      uro_ifc_building_installation_attribute{}.uro_ifc_space_base_quantity_uro_clear_height xml_real64, uro_ifc_building_installation_attribute{}.uro_ifc_space_base_quantity_uro_clear_height_units xml_buffer, uro_ifc_building_installation_attribute{}.uro_ifc_space_base_quantity_uro_finish_ceiling_height xml_real64, uro_ifc_building_installation_attribute{}.uro_ifc_space_base_quantity_uro_finish_ceiling_height_units xml_buffer, uro_ifc_building_installation_attribute{}.uro_ifc_space_base_quantity_uro_gross_perimeter xml_real64, uro_ifc_building_installation_attribute{}.uro_ifc_space_base_quantity_uro_gross_perimeter_units xml_buffer, uro_ifc_building_installation_attribute{}.uro_ifc_space_base_quantity_uro_net_perimeter xml_real64, uro_ifc_building_installation_attribute{}.uro_ifc_space_base_quantity_uro_net_perimeter_units xml_buffer, uro_ifc_building_installation_attribute{}.uro_ifc_space_base_quantity_uro_gross_ceiling_area xml_real64, uro_ifc_building_installation_attribute{}.uro_ifc_space_base_quantity_uro_gross_ceiling_area_units xml_buffer, uro_ifc_building_installation_attribute{}.uro_ifc_space_base_quantity_uro_gross_floor_area xml_real64, uro_ifc_building_installation_attribute{}.uro_ifc_space_base_quantity_uro_gross_floor_area_units xml_buffer, uro_ifc_building_installation_attribute{}.uro_ifc_space_base_quantity_uro_net_ceiling_area xml_real64, uro_ifc_building_installation_attribute{}.uro_ifc_space_base_quantity_uro_net_ceiling_area_units xml_buffer, uro_ifc_building_installation_attribute{}.uro_ifc_space_base_quantity_uro_net_floor_area xml_real64, uro_ifc_building_installation_attribute{}.uro_ifc_space_base_quantity_uro_net_floor_area_units xml_buffer, uro_ifc_building_installation_attribute{}.uro_ifc_space_base_quantity_uro_gross_wall_area xml_real64, uro_ifc_building_installation_attribute{}.uro_ifc_space_base_quantity_uro_gross_wall_area_units xml_buffer, uro_ifc_building_installation_attribute{}.uro_ifc_space_base_quantity_uro_net_wall_area xml_real64, uro_ifc_building_installation_attribute{}.uro_ifc_space_base_quantity_uro_net_wall_area_units xml_buffer, uro_ifc_building_installation_attribute{}.uro_ifc_space_base_quantity_uro_gross_volume xml_real64, uro_ifc_building_installation_attribute{}.uro_ifc_space_base_quantity_uro_gross_volume_units xml_buffer, uro_ifc_building_installation_attribute{}.uro_ifc_space_base_quantity_uro_net_volume xml_real64, uro_ifc_building_installation_attribute{}.uro_ifc_space_base_quantity_uro_net_volume_units xml_buffer, uro_ifc_building_installation_attribute{}.uro_ifc_wall_uro_global_id xml_buffer, uro_ifc_building_installation_attribute{}.uro_ifc_wall_uro_name xml_buffer, uro_ifc_building_installation_attribute{}.uro_ifc_wall_uro_description xml_buffer, uro_ifc_building_installation_attribute{}.uro_ifc_wall_uro_object_type xml_buffer, uro_ifc_building_installation_attribute{}.uro_ifc_wall_uro_tag xml_buffer, uro_ifc_building_installation_attribute{}.uro_ifc_wall_uro_element_type xml_buffer,
      uro_ifc_building_installation_attribute{}.uro_ifc_wall_uro_element_type_codeSpace xml_buffer, uro_ifc_building_installation_attribute{}.uro_ifc_wall_uro_predefined_type xml_buffer, uro_ifc_building_installation_attribute{}.uro_ifc_wall_uro_predefined_type_codeSpace xml_buffer, uro_ifc_building_installation_attribute{}.uro_ifc_wall_uro_shape_type xml_buffer, uro_ifc_building_installation_attribute{}.uro_ifc_wall_uro_shape_type_codeSpace xml_buffer, uro_ifc_building_installation_attribute{}.uro_ifc_wall_uro_number_of_riser xml_int64, uro_ifc_building_installation_attribute{}.uro_ifc_wall_uro_number_of_treads xml_int64, uro_ifc_building_installation_attribute{}.uro_ifc_wall_uro_riser_height xml_int64, uro_ifc_building_installation_attribute{}.uro_ifc_wall_uro_tread_length xml_int64, uro_ifc_building_installation_attribute{}.uro_ifc_wall_uro_operation_type xml_char(11), uro_ifc_building_installation_attribute{}.uro_ifc_wall_uro_capacity_by_weight xml_real64, uro_ifc_building_installation_attribute{}.uro_ifc_wall_uro_capacity_by_weight_units xml_buffer, uro_ifc_building_installation_attribute{}.uro_ifc_wall_uro_capacity_by_number xml_int64, uro_ifc_building_installation_attribute{}.uro_ifc_wall_uro_nominal_length xml_real64, uro_ifc_building_installation_attribute{}.uro_ifc_wall_uro_nominal_length_units xml_buffer, uro_ifc_building_installation_attribute{}.uro_ifc_wall_uro_nominal_width xml_real64, uro_ifc_building_installation_attribute{}.uro_ifc_wall_uro_nominal_width_units xml_buffer, uro_ifc_building_installation_attribute{}.uro_ifc_wall_uro_nominal_height xml_real64, uro_ifc_building_installation_attribute{}.uro_ifc_wall_uro_nominal_height_units xml_buffer, uro_ifc_building_installation_attribute{}.uro_ifc_wall_uro_gross_foot_print_area xml_real64, uro_ifc_building_installation_attribute{}.uro_ifc_wall_uro_gross_foot_print_area_units xml_buffer, uro_ifc_building_installation_attribute{}.uro_ifc_wall_uro_net_foot_print_area xml_real64, uro_ifc_building_installation_attribute{}.uro_ifc_wall_uro_net_foot_print_area_units xml_buffer, uro_ifc_building_installation_attribute{}.uro_ifc_wall_uro_gross_side_area xml_real64, uro_ifc_building_installation_attribute{}.uro_ifc_wall_uro_gross_side_area_units xml_buffer, uro_ifc_building_installation_attribute{}.uro_ifc_wall_uro_net_side_area xml_real64, uro_ifc_building_installation_attribute{}.uro_ifc_wall_uro_net_side_area_units xml_buffer, uro_ifc_building_installation_attribute{}.uro_ifc_wall_uro_gross_side_area_left xml_real64, uro_ifc_building_installation_attribute{}.uro_ifc_wall_uro_gross_side_area_left_units xml_buffer, uro_ifc_building_installation_attribute{}.uro_ifc_wall_uro_net_side_area_left xml_real64,
      uro_ifc_building_installation_attribute{}.uro_ifc_wall_uro_net_side_area_left_units xml_buffer, uro_ifc_building_installation_attribute{}.uro_ifc_wall_uro_gross_side_area_right xml_real64, uro_ifc_building_installation_attribute{}.uro_ifc_wall_uro_gross_side_area_right_units xml_buffer, uro_ifc_building_installation_attribute{}.uro_ifc_wall_uro_net_side_area_right xml_real64, uro_ifc_building_installation_attribute{}.uro_ifc_wall_uro_net_side_area_right_units xml_buffer, uro_ifc_building_installation_attribute{}.uro_ifc_wall_uro_gross_volume xml_real64, uro_ifc_building_installation_attribute{}.uro_ifc_wall_uro_gross_volume_units xml_buffer, uro_ifc_building_installation_attribute{}.uro_ifc_wall_uro_net_volume xml_real64, uro_ifc_building_installation_attribute{}.uro_ifc_wall_uro_net_volume_units xml_buffer, uro_ifc_building_installation_attribute{}.uro_ifc_wall_standard_case_uro_global_id xml_buffer, uro_ifc_building_installation_attribute{}.uro_ifc_wall_standard_case_uro_name xml_buffer, uro_ifc_building_installation_attribute{}.uro_ifc_wall_standard_case_uro_description xml_buffer, uro_ifc_building_installation_attribute{}.uro_ifc_wall_standard_case_uro_object_type xml_buffer, uro_ifc_building_installation_attribute{}.uro_ifc_wall_standard_case_uro_tag xml_buffer, uro_ifc_building_installation_attribute{}.uro_ifc_wall_standard_case_uro_element_type xml_buffer, uro_ifc_building_installation_attribute{}.uro_ifc_wall_standard_case_uro_element_type_codeSpace xml_buffer, uro_ifc_building_installation_attribute{}.uro_ifc_wall_standard_case_uro_predefined_type xml_buffer, uro_ifc_building_installation_attribute{}.uro_ifc_wall_standard_case_uro_predefined_type_codeSpace xml_buffer, uro_ifc_building_installation_attribute{}.uro_ifc_wall_standard_case_uro_shape_type xml_buffer, uro_ifc_building_installation_attribute{}.uro_ifc_wall_standard_case_uro_shape_type_codeSpace xml_buffer, uro_ifc_building_installation_attribute{}.uro_ifc_wall_standard_case_uro_number_of_riser xml_int64, uro_ifc_building_installation_attribute{}.uro_ifc_wall_standard_case_uro_number_of_treads xml_int64, uro_ifc_building_installation_attribute{}.uro_ifc_wall_standard_case_uro_riser_height xml_int64, uro_ifc_building_installation_attribute{}.uro_ifc_wall_standard_case_uro_tread_length xml_int64, uro_ifc_building_installation_attribute{}.uro_ifc_wall_standard_case_uro_operation_type xml_char(11), uro_ifc_building_installation_attribute{}.uro_ifc_wall_standard_case_uro_capacity_by_weight xml_real64, uro_ifc_building_installation_attribute{}.uro_ifc_wall_standard_case_uro_capacity_by_weight_units xml_buffer, uro_ifc_building_installation_attribute{}.uro_ifc_wall_standard_case_uro_capacity_by_number xml_int64, uro_ifc_building_installation_attribute{}.uro_ifc_wall_standard_case_uro_nominal_length xml_real64, uro_ifc_building_installation_attribute{}.uro_ifc_wall_standard_case_uro_nominal_length_units xml_buffer,
      uro_ifc_building_installation_attribute{}.uro_ifc_wall_standard_case_uro_nominal_width xml_real64, uro_ifc_building_installation_attribute{}.uro_ifc_wall_standard_case_uro_nominal_width_units xml_buffer, uro_ifc_building_installation_attribute{}.uro_ifc_wall_standard_case_uro_nominal_height xml_real64, uro_ifc_building_installation_attribute{}.uro_ifc_wall_standard_case_uro_nominal_height_units xml_buffer, uro_ifc_building_installation_attribute{}.uro_ifc_wall_standard_case_uro_gross_foot_print_area xml_real64, uro_ifc_building_installation_attribute{}.uro_ifc_wall_standard_case_uro_gross_foot_print_area_units xml_buffer, uro_ifc_building_installation_attribute{}.uro_ifc_wall_standard_case_uro_net_foot_print_area xml_real64, uro_ifc_building_installation_attribute{}.uro_ifc_wall_standard_case_uro_net_foot_print_area_units xml_buffer, uro_ifc_building_installation_attribute{}.uro_ifc_wall_standard_case_uro_gross_side_area xml_real64, uro_ifc_building_installation_attribute{}.uro_ifc_wall_standard_case_uro_gross_side_area_units xml_buffer, uro_ifc_building_installation_attribute{}.uro_ifc_wall_standard_case_uro_net_side_area xml_real64, uro_ifc_building_installation_attribute{}.uro_ifc_wall_standard_case_uro_net_side_area_units xml_buffer, uro_ifc_building_installation_attribute{}.uro_ifc_wall_standard_case_uro_gross_side_area_left xml_real64, uro_ifc_building_installation_attribute{}.uro_ifc_wall_standard_case_uro_gross_side_area_left_units xml_buffer, uro_ifc_building_installation_attribute{}.uro_ifc_wall_standard_case_uro_net_side_area_left xml_real64, uro_ifc_building_installation_attribute{}.uro_ifc_wall_standard_case_uro_net_side_area_left_units xml_buffer, uro_ifc_building_installation_attribute{}.uro_ifc_wall_standard_case_uro_gross_side_area_right xml_real64, uro_ifc_building_installation_attribute{}.uro_ifc_wall_standard_case_uro_gross_side_area_right_units xml_buffer, uro_ifc_building_installation_attribute{}.uro_ifc_wall_standard_case_uro_net_side_area_right xml_real64, uro_ifc_building_installation_attribute{}.uro_ifc_wall_standard_case_uro_net_side_area_right_units xml_buffer, uro_ifc_building_installation_attribute{}.uro_ifc_wall_standard_case_uro_gross_volume xml_real64, uro_ifc_building_installation_attribute{}.uro_ifc_wall_standard_case_uro_gross_volume_units xml_buffer, uro_ifc_building_installation_attribute{}.uro_ifc_wall_standard_case_uro_net_volume xml_real64, uro_ifc_building_installation_attribute{}.uro_ifc_wall_standard_case_uro_net_volume_units xml_buffer, uro_ifc_building_installation_attribute{}.uro_ifc_window_uro_global_id xml_buffer, uro_ifc_building_installation_attribute{}.uro_ifc_window_uro_name xml_buffer, uro_ifc_building_installation_attribute{}.uro_ifc_window_uro_description xml_buffer, uro_ifc_building_installation_attribute{}.uro_ifc_window_uro_object_type xml_buffer, uro_ifc_building_installation_attribute{}.uro_ifc_window_uro_tag xml_buffer, uro_ifc_building_installation_attribute{}.uro_ifc_window_uro_element_type xml_buffer,
      uro_ifc_building_installation_attribute{}.uro_ifc_window_uro_element_type_codeSpace xml_buffer, uro_ifc_building_installation_attribute{}.uro_ifc_window_uro_predefined_type xml_buffer, uro_ifc_building_installation_attribute{}.uro_ifc_window_uro_predefined_type_codeSpace xml_buffer, uro_ifc_building_installation_attribute{}.uro_ifc_window_uro_shape_type xml_buffer, uro_ifc_building_installation_attribute{}.uro_ifc_window_uro_shape_type_codeSpace xml_buffer, uro_ifc_building_installation_attribute{}.uro_ifc_window_uro_number_of_riser xml_int64, uro_ifc_building_installation_attribute{}.uro_ifc_window_uro_number_of_treads xml_int64, uro_ifc_building_installation_attribute{}.uro_ifc_window_uro_riser_height xml_int64, uro_ifc_building_installation_attribute{}.uro_ifc_window_uro_tread_length xml_int64, uro_ifc_building_installation_attribute{}.uro_ifc_window_uro_operation_type xml_char(11), uro_ifc_building_installation_attribute{}.uro_ifc_window_uro_capacity_by_weight xml_real64, uro_ifc_building_installation_attribute{}.uro_ifc_window_uro_capacity_by_weight_units xml_buffer, uro_ifc_building_installation_attribute{}.uro_ifc_window_uro_capacity_by_number xml_int64, uro_ifc_building_installation_attribute{}.uro_ifc_window_uro_overall_height xml_real64, uro_ifc_building_installation_attribute{}.uro_ifc_window_uro_overall_height_units xml_buffer, uro_ifc_building_installation_attribute{}.uro_ifc_window_uro_overall_width xml_real64, uro_ifc_building_installation_attribute{}.uro_ifc_window_uro_overall_width_units xml_buffer
Junction_47
Tester_IfcFurnishingElement
    BOOL_OP = OR
    TEST_CLAUSE = TEST $(DEST_LOD) = 4.3
    TEST_MODE = TEST
    PASSED -> GeometryRefiner_3
PLATEAU.IfcReprojector
    DEST_COORDSYS = $(DEST_COORDSYS)
    LENGTH_MULTIPLIER = @Value(_lengthmultiplier)
    REPROJECTION_PARAMS = @Value(_reprojection_params)
    Reprojected -> BuildingFurniture (writer CITYGML_2)
BuildingFurniture (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_level_of_detail{} xml_buffer, uro_ifc_building_furniture_attribute{}.uro_ifc_building_uro_global_id xml_buffer, uro_ifc_building_furniture_attribute{}.uro_ifc_building_uro_name xml_buffer, uro_ifc_building_furniture_attribute{}.uro_ifc_building_uro_description xml_buffer, uro_ifc_building_furniture_attribute{}.uro_ifc_building_uro_object_type xml_buffer, uro_ifc_building_furniture_attribute{}.uro_ifc_building_uro_long_name xml_buffer, uro_ifc_building_furniture_attribute{}.uro_ifc_building_uro_composition_type xml_char(7), uro_ifc_building_furniture_attribute{}.uro_ifc_building_uro_elevation_of_ref_height xml_real64, uro_ifc_building_furniture_attribute{}.uro_ifc_building_uro_elevation_of_ref_height_units xml_buffer, uro_ifc_building_furniture_attribute{}.uro_ifc_building_uro_elevation_of_terrain xml_real64,
      uro_ifc_building_furniture_attribute{}.uro_ifc_building_uro_elevation_of_terrain_units xml_buffer, uro_ifc_building_furniture_attribute{}.uro_ifc_building_uro_building_address_xlink_href xml_buffer, uro_ifc_building_furniture_attribute{}.uro_ifc_building_element_uro_global_id xml_buffer, uro_ifc_building_furniture_attribute{}.uro_ifc_building_element_uro_name xml_buffer, uro_ifc_building_furniture_attribute{}.uro_ifc_building_element_uro_description xml_buffer, uro_ifc_building_furniture_attribute{}.uro_ifc_building_element_uro_object_type xml_buffer, uro_ifc_building_furniture_attribute{}.uro_ifc_building_element_uro_tag xml_buffer, uro_ifc_building_furniture_attribute{}.uro_ifc_building_element_uro_element_type xml_buffer, uro_ifc_building_furniture_attribute{}.uro_ifc_building_element_uro_element_type_codeSpace xml_buffer, uro_ifc_building_furniture_attribute{}.uro_ifc_building_element_uro_predefined_type xml_buffer, uro_ifc_building_furniture_attribute{}.uro_ifc_building_element_uro_predefined_type_codeSpace xml_buffer, uro_ifc_building_furniture_attribute{}.uro_ifc_building_element_uro_shape_type xml_buffer, uro_ifc_building_furniture_attribute{}.uro_ifc_building_element_uro_shape_type_codeSpace xml_buffer, uro_ifc_building_furniture_attribute{}.uro_ifc_building_element_uro_number_of_riser xml_int64, uro_ifc_building_furniture_attribute{}.uro_ifc_building_element_uro_number_of_treads xml_int64, uro_ifc_building_furniture_attribute{}.uro_ifc_building_element_uro_riser_height xml_int64, uro_ifc_building_furniture_attribute{}.uro_ifc_building_element_uro_tread_length xml_int64, uro_ifc_building_furniture_attribute{}.uro_ifc_building_element_uro_operation_type xml_char(11), uro_ifc_building_furniture_attribute{}.uro_ifc_building_element_uro_capacity_by_weight xml_real64, uro_ifc_building_furniture_attribute{}.uro_ifc_building_element_uro_capacity_by_weight_units xml_buffer, uro_ifc_building_furniture_attribute{}.uro_ifc_building_element_uro_capacity_by_number xml_int64, uro_ifc_building_furniture_attribute{}.uro_ifc_building_storey_uro_global_id xml_buffer, uro_ifc_building_furniture_attribute{}.uro_ifc_building_storey_uro_name xml_buffer, uro_ifc_building_furniture_attribute{}.uro_ifc_building_storey_uro_description xml_buffer, uro_ifc_building_furniture_attribute{}.uro_ifc_building_storey_uro_object_type xml_buffer, uro_ifc_building_furniture_attribute{}.uro_ifc_building_storey_uro_long_name xml_buffer, uro_ifc_building_furniture_attribute{}.uro_ifc_building_storey_uro_composition_type xml_char(7), uro_ifc_building_furniture_attribute{}.uro_ifc_building_storey_uro_elevation xml_real64, uro_ifc_building_furniture_attribute{}.uro_ifc_building_storey_uro_elevation_units xml_buffer, uro_ifc_building_furniture_attribute{}.uro_ifc_classification_reference_uro_location xml_buffer,
      uro_ifc_building_furniture_attribute{}.uro_ifc_classification_reference_uro_item_reference xml_buffer, uro_ifc_building_furniture_attribute{}.uro_ifc_classification_reference_uro_item_reference_codeSpace xml_buffer, uro_ifc_building_furniture_attribute{}.uro_ifc_classification_reference_uro_name xml_buffer, uro_ifc_building_furniture_attribute{}.uro_ifc_classification_reference_uro_name_codeSpace xml_buffer, uro_ifc_building_furniture_attribute{}.uro_ifc_classification_reference_uro_reference_source_uro_ifc_classification_uro_source xml_buffer, uro_ifc_building_furniture_attribute{}.uro_ifc_classification_reference_uro_reference_source_uro_ifc_classification_uro_edition xml_buffer, uro_ifc_building_furniture_attribute{}.uro_ifc_classification_reference_uro_reference_source_uro_ifc_classification_uro_edition_date xml_date, uro_ifc_building_furniture_attribute{}.uro_ifc_classification_reference_uro_reference_source_uro_ifc_classification_uro_name xml_buffer, uro_ifc_building_furniture_attribute{}.uro_ifc_coordinate_reference_system_uro_name xml_buffer, uro_ifc_building_furniture_attribute{}.uro_ifc_coordinate_reference_system_uro_description xml_buffer, uro_ifc_building_furniture_attribute{}.uro_ifc_coordinate_reference_system_uro_geodetic_datum xml_buffer, uro_ifc_building_furniture_attribute{}.uro_ifc_coordinate_reference_system_uro_vertical_datum xml_buffer, uro_ifc_building_furniture_attribute{}.uro_ifc_curtain_wall_uro_global_id xml_buffer, uro_ifc_building_furniture_attribute{}.uro_ifc_curtain_wall_uro_name xml_buffer, uro_ifc_building_furniture_attribute{}.uro_ifc_curtain_wall_uro_description xml_buffer, uro_ifc_building_furniture_attribute{}.uro_ifc_curtain_wall_uro_object_type xml_buffer, uro_ifc_building_furniture_attribute{}.uro_ifc_curtain_wall_uro_tag xml_buffer, uro_ifc_building_furniture_attribute{}.uro_ifc_curtain_wall_uro_element_type xml_buffer, uro_ifc_building_furniture_attribute{}.uro_ifc_curtain_wall_uro_element_type_codeSpace xml_buffer, uro_ifc_building_furniture_attribute{}.uro_ifc_curtain_wall_uro_predefined_type xml_buffer, uro_ifc_building_furniture_attribute{}.uro_ifc_curtain_wall_uro_predefined_type_codeSpace xml_buffer, uro_ifc_building_furniture_attribute{}.uro_ifc_curtain_wall_uro_shape_type xml_buffer, uro_ifc_building_furniture_attribute{}.uro_ifc_curtain_wall_uro_shape_type_codeSpace xml_buffer, uro_ifc_building_furniture_attribute{}.uro_ifc_curtain_wall_uro_number_of_riser xml_int64, uro_ifc_building_furniture_attribute{}.uro_ifc_curtain_wall_uro_number_of_treads xml_int64, uro_ifc_building_furniture_attribute{}.uro_ifc_curtain_wall_uro_riser_height xml_int64, uro_ifc_building_furniture_attribute{}.uro_ifc_curtain_wall_uro_tread_length xml_int64, uro_ifc_building_furniture_attribute{}.uro_ifc_curtain_wall_uro_operation_type xml_char(11), uro_ifc_building_furniture_attribute{}.uro_ifc_curtain_wall_uro_capacity_by_weight xml_real64, uro_ifc_building_furniture_attribute{}.uro_ifc_curtain_wall_uro_capacity_by_weight_units xml_buffer,
      uro_ifc_building_furniture_attribute{}.uro_ifc_curtain_wall_uro_capacity_by_number xml_int64, uro_ifc_building_furniture_attribute{}.uro_ifc_door_uro_global_id xml_buffer, uro_ifc_building_furniture_attribute{}.uro_ifc_door_uro_name xml_buffer, uro_ifc_building_furniture_attribute{}.uro_ifc_door_uro_description xml_buffer, uro_ifc_building_furniture_attribute{}.uro_ifc_door_uro_object_type xml_buffer, uro_ifc_building_furniture_attribute{}.uro_ifc_door_uro_tag xml_buffer, uro_ifc_building_furniture_attribute{}.uro_ifc_door_uro_element_type xml_buffer, uro_ifc_building_furniture_attribute{}.uro_ifc_door_uro_element_type_codeSpace xml_buffer, uro_ifc_building_furniture_attribute{}.uro_ifc_door_uro_predefined_type xml_buffer, uro_ifc_building_furniture_attribute{}.uro_ifc_door_uro_predefined_type_codeSpace xml_buffer, uro_ifc_building_furniture_attribute{}.uro_ifc_door_uro_shape_type xml_buffer, uro_ifc_building_furniture_attribute{}.uro_ifc_door_uro_shape_type_codeSpace xml_buffer, uro_ifc_building_furniture_attribute{}.uro_ifc_door_uro_number_of_riser xml_int64, uro_ifc_building_furniture_attribute{}.uro_ifc_door_uro_number_of_treads xml_int64, uro_ifc_building_furniture_attribute{}.uro_ifc_door_uro_riser_height xml_int64, uro_ifc_building_furniture_attribute{}.uro_ifc_door_uro_tread_length xml_int64, uro_ifc_building_furniture_attribute{}.uro_ifc_door_uro_operation_type xml_char(11), uro_ifc_building_furniture_attribute{}.uro_ifc_door_uro_capacity_by_weight xml_real64, uro_ifc_building_furniture_attribute{}.uro_ifc_door_uro_capacity_by_weight_units xml_buffer, uro_ifc_building_furniture_attribute{}.uro_ifc_door_uro_capacity_by_number xml_int64, uro_ifc_building_furniture_attribute{}.uro_ifc_door_uro_overall_height xml_real64, uro_ifc_building_furniture_attribute{}.uro_ifc_door_uro_overall_height_units xml_buffer, uro_ifc_building_furniture_attribute{}.uro_ifc_door_uro_overall_width xml_real64, uro_ifc_building_furniture_attribute{}.uro_ifc_door_uro_overall_width_units xml_buffer, uro_ifc_building_furniture_attribute{}.uro_ifc_furnishing_element_uro_global_id xml_buffer, uro_ifc_building_furniture_attribute{}.uro_ifc_furnishing_element_uro_name xml_buffer, uro_ifc_building_furniture_attribute{}.uro_ifc_furnishing_element_uro_description xml_buffer, uro_ifc_building_furniture_attribute{}.uro_ifc_furnishing_element_uro_object_type xml_buffer, uro_ifc_building_furniture_attribute{}.uro_ifc_furnishing_element_uro_tag xml_buffer, uro_ifc_building_furniture_attribute{}.uro_ifc_map_conversion_uro_source_crs_uro_crs_uro_ifc_projected_crs_uro_name xml_buffer,
      uro_ifc_building_furniture_attribute{}.uro_ifc_map_conversion_uro_source_crs_uro_crs_uro_ifc_projected_crs_uro_description xml_buffer, uro_ifc_building_furniture_attribute{}.uro_ifc_map_conversion_uro_source_crs_uro_crs_uro_ifc_projected_crs_uro_geodetic_datum xml_buffer, uro_ifc_building_furniture_attribute{}.uro_ifc_map_conversion_uro_source_crs_uro_crs_uro_ifc_projected_crs_uro_vertical_datum xml_buffer, uro_ifc_building_furniture_attribute{}.uro_ifc_map_conversion_uro_source_crs_uro_crs_uro_ifc_projected_crs_uro_map_unit xml_buffer, uro_ifc_building_furniture_attribute{}.uro_ifc_map_conversion_uro_source_crs_uro_crs_uro_ifc_projected_crs_uro_map_projection xml_buffer, uro_ifc_building_furniture_attribute{}.uro_ifc_map_conversion_uro_source_crs_uro_crs_uro_ifc_projected_crs_uro_map_zone xml_buffer, uro_ifc_building_furniture_attribute{}.uro_ifc_map_conversion_uro_source_crs_uro_crs_uro_ifc_coordinate_reference_system_uro_name xml_buffer, uro_ifc_building_furniture_attribute{}.uro_ifc_map_conversion_uro_source_crs_uro_crs_uro_ifc_coordinate_reference_system_uro_description xml_buffer, uro_ifc_building_furniture_attribute{}.uro_ifc_map_conversion_uro_source_crs_uro_crs_uro_ifc_coordinate_reference_system_uro_geodetic_datum xml_buffer, uro_ifc_building_furniture_attribute{}.uro_ifc_map_conversion_uro_source_crs_uro_crs_uro_ifc_coordinate_reference_system_uro_vertical_datum xml_buffer, uro_ifc_building_furniture_attribute{}.uro_ifc_map_conversion_uro_source_crs_uro_context_uro_ifc_geometric_representation_context_uro_context_identifier xml_buffer, uro_ifc_building_furniture_attribute{}.uro_ifc_map_conversion_uro_source_crs_uro_context_uro_ifc_geometric_representation_context_uro_context_type xml_buffer, uro_ifc_building_furniture_attribute{}.uro_ifc_map_conversion_uro_source_crs_uro_context_uro_ifc_geometric_representation_context_uro_coordinate_space_dimension xml_int64, uro_ifc_building_furniture_attribute{}.uro_ifc_map_conversion_uro_source_crs_uro_context_uro_ifc_geometric_representation_context_uro_precision xml_real64, uro_ifc_building_furniture_attribute{}.uro_ifc_map_conversion_uro_source_crs_uro_context_uro_ifc_geometric_representation_context_uro_true_north xml_real64, uro_ifc_building_furniture_attribute{}.uro_ifc_map_conversion_uro_target_crs_uro_ifc_projected_crs_uro_name xml_buffer, uro_ifc_building_furniture_attribute{}.uro_ifc_map_conversion_uro_target_crs_uro_ifc_projected_crs_uro_description xml_buffer, uro_ifc_building_furniture_attribute{}.uro_ifc_map_conversion_uro_target_crs_uro_ifc_projected_crs_uro_geodetic_datum xml_buffer, uro_ifc_building_furniture_attribute{}.uro_ifc_map_conversion_uro_target_crs_uro_ifc_projected_crs_uro_vertical_datum xml_buffer, uro_ifc_building_furniture_attribute{}.uro_ifc_map_conversion_uro_target_crs_uro_ifc_projected_crs_uro_map_unit xml_buffer, uro_ifc_building_furniture_attribute{}.uro_ifc_map_conversion_uro_target_crs_uro_ifc_projected_crs_uro_map_projection xml_buffer, uro_ifc_building_furniture_attribute{}.uro_ifc_map_conversion_uro_target_crs_uro_ifc_projected_crs_uro_map_zone xml_buffer, uro_ifc_building_furniture_attribute{}.uro_ifc_map_conversion_uro_target_crs_uro_ifc_coordinate_reference_system_uro_name xml_buffer, uro_ifc_building_furniture_attribute{}.uro_ifc_map_conversion_uro_target_crs_uro_ifc_coordinate_reference_system_uro_description xml_buffer, uro_ifc_building_furniture_attribute{}.uro_ifc_map_conversion_uro_target_crs_uro_ifc_coordinate_reference_system_uro_geodetic_datum xml_buffer, uro_ifc_building_furniture_attribute{}.uro_ifc_map_conversion_uro_target_crs_uro_ifc_coordinate_reference_system_uro_vertical_datum xml_buffer, uro_ifc_building_furniture_attribute{}.uro_ifc_map_conversion_uro_eastings xml_buffer, uro_ifc_building_furniture_attribute{}.uro_ifc_map_conversion_uro_northings xml_buffer, uro_ifc_building_furniture_attribute{}.uro_ifc_map_conversion_uro_orthogonal_height xml_real64, uro_ifc_building_furniture_attribute{}.uro_ifc_map_conversion_uro_orthogonal_height_units xml_buffer,
      uro_ifc_building_furniture_attribute{}.uro_ifc_map_conversion_uro_x_axis_abscissa xml_real64, uro_ifc_building_furniture_attribute{}.uro_ifc_map_conversion_uro_x_axis_ordinate xml_real64, uro_ifc_building_furniture_attribute{}.uro_ifc_map_conversion_uro_scale xml_real64, uro_ifc_building_furniture_attribute{}.uro_ifc_opening_element_uro_global_id xml_buffer, uro_ifc_building_furniture_attribute{}.uro_ifc_opening_element_uro_name xml_buffer, uro_ifc_building_furniture_attribute{}.uro_ifc_opening_element_uro_description xml_buffer, uro_ifc_building_furniture_attribute{}.uro_ifc_opening_element_uro_object_type xml_buffer, uro_ifc_building_furniture_attribute{}.uro_ifc_opening_element_uro_tag xml_buffer, uro_ifc_building_furniture_attribute{}.uro_ifc_opening_element_uro_nominal_area xml_real64, uro_ifc_building_furniture_attribute{}.uro_ifc_opening_element_uro_nominal_area_units xml_buffer, uro_ifc_building_furniture_attribute{}.uro_ifc_opening_element_uro_nominal_volume xml_real64, uro_ifc_building_furniture_attribute{}.uro_ifc_opening_element_uro_nominal_volume_units xml_buffer, uro_ifc_building_furniture_attribute{}.uro_ifc_project_uro_global_id xml_buffer, uro_ifc_building_furniture_attribute{}.uro_ifc_project_uro_name xml_buffer, uro_ifc_building_furniture_attribute{}.uro_ifc_project_uro_description xml_buffer, uro_ifc_building_furniture_attribute{}.uro_ifc_project_uro_object_type xml_buffer, uro_ifc_building_furniture_attribute{}.uro_ifc_project_uro_long_name xml_buffer, uro_ifc_building_furniture_attribute{}.uro_ifc_project_uro_phase xml_buffer, uro_ifc_building_furniture_attribute{}.uro_ifc_project_uro_representation_contexts_uro_ifc_geometric_representation_context_uro_context_identifier xml_buffer, uro_ifc_building_furniture_attribute{}.uro_ifc_project_uro_representation_contexts_uro_ifc_geometric_representation_context_uro_context_type xml_buffer, uro_ifc_building_furniture_attribute{}.uro_ifc_project_uro_representation_contexts_uro_ifc_geometric_representation_context_uro_coordinate_space_dimension xml_int64, uro_ifc_building_furniture_attribute{}.uro_ifc_project_uro_representation_contexts_uro_ifc_geometric_representation_context_uro_precision xml_real64, uro_ifc_building_furniture_attribute{}.uro_ifc_project_uro_representation_contexts_uro_ifc_geometric_representation_context_uro_true_north xml_real64, uro_ifc_building_furniture_attribute{}.uro_ifc_project_uro_units_in_context{}.uro_ifc_unit_uro_dimensions xml_int64, uro_ifc_building_furniture_attribute{}.uro_ifc_project_uro_units_in_context{}.uro_ifc_unit_uro_unit_type xml_char(28), uro_ifc_building_furniture_attribute{}.uro_ifc_project_uro_units_in_context{}.uro_ifc_unit_uro_perfix xml_buffer, uro_ifc_building_furniture_attribute{}.uro_ifc_project_uro_units_in_context{}.uro_ifc_unit_uro_name xml_buffer, uro_ifc_building_furniture_attribute{}.uro_ifc_projected_crs_uro_name xml_buffer, uro_ifc_building_furniture_attribute{}.uro_ifc_projected_crs_uro_description xml_buffer, uro_ifc_building_furniture_attribute{}.uro_ifc_projected_crs_uro_geodetic_datum xml_buffer,
      uro_ifc_building_furniture_attribute{}.uro_ifc_projected_crs_uro_vertical_datum xml_buffer, uro_ifc_building_furniture_attribute{}.uro_ifc_projected_crs_uro_map_unit xml_buffer, uro_ifc_building_furniture_attribute{}.uro_ifc_projected_crs_uro_map_projection xml_buffer, uro_ifc_building_furniture_attribute{}.uro_ifc_projected_crs_uro_map_zone xml_buffer, uro_ifc_building_furniture_attribute{}.uro_ifc_pset_building_common_uro_building_id xml_real64, uro_ifc_building_furniture_attribute{}.uro_ifc_pset_building_common_uro_building_id_units xml_buffer, uro_ifc_building_furniture_attribute{}.uro_ifc_pset_building_common_uro_is_permanent_id xml_real64, uro_ifc_building_furniture_attribute{}.uro_ifc_pset_building_common_uro_is_permanent_id_units xml_buffer, uro_ifc_building_furniture_attribute{}.uro_ifc_pset_building_common_uro_main_fire_use xml_buffer, uro_ifc_building_furniture_attribute{}.uro_ifc_pset_building_common_uro_ancillary_fire_use xml_buffer, uro_ifc_building_furniture_attribute{}.uro_ifc_pset_building_common_uro_sprinkler_protection xml_boolean, uro_ifc_building_furniture_attribute{}.uro_ifc_pset_building_common_uro_sprinkler_protection_automatic xml_boolean, uro_ifc_building_furniture_attribute{}.uro_ifc_pset_building_common_uro_occupancy_type xml_buffer, uro_ifc_building_furniture_attribute{}.uro_ifc_pset_building_common_uro_occupancy_type_codeSpace xml_buffer, uro_ifc_building_furniture_attribute{}.uro_ifc_pset_building_common_uro_gross_planned_area xml_real64, uro_ifc_building_furniture_attribute{}.uro_ifc_pset_building_common_uro_gross_planned_area_units xml_buffer, uro_ifc_building_furniture_attribute{}.uro_ifc_pset_building_common_uro_number_of_storeys xml_int64, uro_ifc_building_furniture_attribute{}.uro_ifc_pset_building_common_uro_year_of_construction xml_buffer, uro_ifc_building_furniture_attribute{}.uro_ifc_pset_building_common_uro_is_landmarked xml_boolean, uro_ifc_building_furniture_attribute{}.uro_ifc_pset_door_common_uro_reference xml_buffer, uro_ifc_building_furniture_attribute{}.uro_ifc_pset_door_common_uro_acoustic_rating xml_buffer, uro_ifc_building_furniture_attribute{}.uro_ifc_pset_door_common_uro_firerating xml_buffer, uro_ifc_building_furniture_attribute{}.uro_ifc_pset_door_common_uro_security_rating xml_buffer, uro_ifc_building_furniture_attribute{}.uro_ifc_pset_door_common_uro_is_external xml_boolean, uro_ifc_building_furniture_attribute{}.uro_ifc_pset_door_common_uro_infiltration xml_real64, uro_ifc_building_furniture_attribute{}.uro_ifc_pset_door_common_uro_thermal_transmittance xml_real64, uro_ifc_building_furniture_attribute{}.uro_ifc_pset_door_common_uro_glazing_area_fraction xml_real64, uro_ifc_building_furniture_attribute{}.uro_ifc_pset_door_common_uro_handicap_accessible xml_real64, uro_ifc_building_furniture_attribute{}.uro_ifc_pset_door_common_uro_fire_exit xml_boolean, uro_ifc_building_furniture_attribute{}.uro_ifc_pset_door_common_uro_self_closing xml_real64,
      uro_ifc_building_furniture_attribute{}.uro_ifc_pset_door_common_uro_smoke_stop xml_boolean, uro_ifc_building_furniture_attribute{}.uro_ifc_pset_opening_element_common_uro_reference xml_buffer, uro_ifc_building_furniture_attribute{}.uro_ifc_pset_opening_element_common_uro_purpose xml_buffer, uro_ifc_building_furniture_attribute{}.uro_ifc_pset_opening_element_common_uro_fire_exit xml_boolean, uro_ifc_building_furniture_attribute{}.uro_ifc_pset_opening_element_common_uro_protected_opening xml_boolean, uro_ifc_building_furniture_attribute{}.uro_ifc_pset_opening_element_common_uro_parallel_jambs xml_boolean, uro_ifc_building_furniture_attribute{}.uro_ifc_pset_site_common_uro_buildable_area xml_real64, uro_ifc_building_furniture_attribute{}.uro_ifc_pset_site_common_uro_buildable_area_units xml_buffer, uro_ifc_building_furniture_attribute{}.uro_ifc_pset_site_common_uro_total_area xml_real64, uro_ifc_building_furniture_attribute{}.uro_ifc_pset_site_common_uro_total_area_units xml_buffer, uro_ifc_building_furniture_attribute{}.uro_ifc_pset_site_common_uro_building_height_limit xml_real64, uro_ifc_building_furniture_attribute{}.uro_ifc_pset_site_common_uro_building_height_limit_units xml_buffer, uro_ifc_building_furniture_attribute{}.uro_ifc_pset_space_common_uro_reference xml_buffer, uro_ifc_building_furniture_attribute{}.uro_ifc_pset_space_common_uro_category xml_buffer, uro_ifc_building_furniture_attribute{}.uro_ifc_pset_space_common_uro_category_codeSpace xml_buffer, uro_ifc_building_furniture_attribute{}.uro_ifc_pset_space_common_uro_floor_covering xml_buffer, uro_ifc_building_furniture_attribute{}.uro_ifc_pset_space_common_uro_wall_covering xml_buffer, uro_ifc_building_furniture_attribute{}.uro_ifc_pset_space_common_uro_ceiling_covering xml_buffer, uro_ifc_building_furniture_attribute{}.uro_ifc_pset_space_common_uro_skirting_covering xml_buffer, uro_ifc_building_furniture_attribute{}.uro_ifc_pset_space_common_uro_gross_planned_area xml_real64, uro_ifc_building_furniture_attribute{}.uro_ifc_pset_space_common_uro_gross_planned_area_units xml_buffer, uro_ifc_building_furniture_attribute{}.uro_ifc_pset_space_common_uro_net_planned_area xml_real64, uro_ifc_building_furniture_attribute{}.uro_ifc_pset_space_common_uro_net_planned_area_units xml_buffer, uro_ifc_building_furniture_attribute{}.uro_ifc_pset_space_common_uro_publicly_accessible xml_boolean, uro_ifc_building_furniture_attribute{}.uro_ifc_pset_space_common_uro_handicap_accessible xml_boolean, uro_ifc_building_furniture_attribute{}.uro_ifc_pset_space_common_uro_concealed_flooring xml_boolean, uro_ifc_building_furniture_attribute{}.uro_ifc_pset_space_common_uro_concealed_ceiling xml_boolean, uro_ifc_building_furniture_attribute{}.uro_ifc_pset_window_common_uro_reference xml_buffer, uro_ifc_building_furniture_attribute{}.uro_ifc_pset_window_common_uro_acoustic_rating xml_buffer, uro_ifc_building_furniture_attribute{}.uro_ifc_pset_window_common_uro_firerating xml_buffer,
      uro_ifc_building_furniture_attribute{}.uro_ifc_pset_window_common_uro_security_rating xml_buffer, uro_ifc_building_furniture_attribute{}.uro_ifc_pset_window_common_uro_is_external xml_boolean, uro_ifc_building_furniture_attribute{}.uro_ifc_pset_window_common_uro_infiltration xml_real64, uro_ifc_building_furniture_attribute{}.uro_ifc_pset_window_common_uro_thermal_transmittance xml_real64, uro_ifc_building_furniture_attribute{}.uro_ifc_pset_window_common_uro_glazing_area_fraction xml_real64, uro_ifc_building_furniture_attribute{}.uro_ifc_pset_window_common_uro_smoke_stop xml_boolean, uro_ifc_building_furniture_attribute{}.uro_ifc_site_uro_global_id xml_buffer, uro_ifc_building_furniture_attribute{}.uro_ifc_site_uro_name xml_buffer, uro_ifc_building_furniture_attribute{}.uro_ifc_site_uro_description xml_buffer, uro_ifc_building_furniture_attribute{}.uro_ifc_site_uro_object_type xml_buffer, uro_ifc_building_furniture_attribute{}.uro_ifc_site_uro_long_name xml_buffer, uro_ifc_building_furniture_attribute{}.uro_ifc_site_uro_composition_type xml_char(7), uro_ifc_building_furniture_attribute{}.uro_ifc_site_uro_ref_longitude xml_real64, uro_ifc_building_furniture_attribute{}.uro_ifc_site_uro_ref_latitude xml_real64, uro_ifc_building_furniture_attribute{}.uro_ifc_site_uro_ref_elevation xml_real64, uro_ifc_building_furniture_attribute{}.uro_ifc_site_uro_ref_elevation_units xml_buffer, uro_ifc_building_furniture_attribute{}.uro_ifc_site_uro_land_title_number xml_buffer, uro_ifc_building_furniture_attribute{}.uro_ifc_site_uro_site_address_xlink_href xml_buffer, uro_ifc_building_furniture_attribute{}.uro_ifc_space_uro_global_id xml_buffer, uro_ifc_building_furniture_attribute{}.uro_ifc_space_uro_name xml_buffer, uro_ifc_building_furniture_attribute{}.uro_ifc_space_uro_description xml_buffer, uro_ifc_building_furniture_attribute{}.uro_ifc_space_uro_object_type xml_buffer, uro_ifc_building_furniture_attribute{}.uro_ifc_space_uro_long_name xml_buffer, uro_ifc_building_furniture_attribute{}.uro_ifc_space_uro_composition_type xml_char(7), uro_ifc_building_furniture_attribute{}.uro_ifc_space_uro_interioror_exterior_space xml_char(10), uro_ifc_building_furniture_attribute{}.uro_ifc_space_uro_elevation_with_flooring xml_real64, uro_ifc_building_furniture_attribute{}.uro_ifc_space_uro_elevation_with_flooring_units xml_buffer, uro_ifc_building_furniture_attribute{}.uro_ifc_space_base_quantity_uro_nominal_height xml_real64, uro_ifc_building_furniture_attribute{}.uro_ifc_space_base_quantity_uro_nominal_height_units xml_buffer, uro_ifc_building_furniture_attribute{}.uro_ifc_space_base_quantity_uro_clear_height xml_real64,
      uro_ifc_building_furniture_attribute{}.uro_ifc_space_base_quantity_uro_clear_height_units xml_buffer, uro_ifc_building_furniture_attribute{}.uro_ifc_space_base_quantity_uro_finish_ceiling_height xml_real64, uro_ifc_building_furniture_attribute{}.uro_ifc_space_base_quantity_uro_finish_ceiling_height_units xml_buffer, uro_ifc_building_furniture_attribute{}.uro_ifc_space_base_quantity_uro_gross_perimeter xml_real64, uro_ifc_building_furniture_attribute{}.uro_ifc_space_base_quantity_uro_gross_perimeter_units xml_buffer, uro_ifc_building_furniture_attribute{}.uro_ifc_space_base_quantity_uro_net_perimeter xml_real64, uro_ifc_building_furniture_attribute{}.uro_ifc_space_base_quantity_uro_net_perimeter_units xml_buffer, uro_ifc_building_furniture_attribute{}.uro_ifc_space_base_quantity_uro_gross_ceiling_area xml_real64, uro_ifc_building_furniture_attribute{}.uro_ifc_space_base_quantity_uro_gross_ceiling_area_units xml_buffer, uro_ifc_building_furniture_attribute{}.uro_ifc_space_base_quantity_uro_gross_floor_area xml_real64, uro_ifc_building_furniture_attribute{}.uro_ifc_space_base_quantity_uro_gross_floor_area_units xml_buffer, uro_ifc_building_furniture_attribute{}.uro_ifc_space_base_quantity_uro_net_ceiling_area xml_real64, uro_ifc_building_furniture_attribute{}.uro_ifc_space_base_quantity_uro_net_ceiling_area_units xml_buffer, uro_ifc_building_furniture_attribute{}.uro_ifc_space_base_quantity_uro_net_floor_area xml_real64, uro_ifc_building_furniture_attribute{}.uro_ifc_space_base_quantity_uro_net_floor_area_units xml_buffer, uro_ifc_building_furniture_attribute{}.uro_ifc_space_base_quantity_uro_gross_wall_area xml_real64, uro_ifc_building_furniture_attribute{}.uro_ifc_space_base_quantity_uro_gross_wall_area_units xml_buffer, uro_ifc_building_furniture_attribute{}.uro_ifc_space_base_quantity_uro_net_wall_area xml_real64, uro_ifc_building_furniture_attribute{}.uro_ifc_space_base_quantity_uro_net_wall_area_units xml_buffer, uro_ifc_building_furniture_attribute{}.uro_ifc_space_base_quantity_uro_gross_volume xml_real64, uro_ifc_building_furniture_attribute{}.uro_ifc_space_base_quantity_uro_gross_volume_units xml_buffer, uro_ifc_building_furniture_attribute{}.uro_ifc_space_base_quantity_uro_net_volume xml_real64, uro_ifc_building_furniture_attribute{}.uro_ifc_space_base_quantity_uro_net_volume_units xml_buffer, uro_ifc_building_furniture_attribute{}.uro_ifc_wall_uro_global_id xml_buffer, uro_ifc_building_furniture_attribute{}.uro_ifc_wall_uro_name xml_buffer, uro_ifc_building_furniture_attribute{}.uro_ifc_wall_uro_description xml_buffer, uro_ifc_building_furniture_attribute{}.uro_ifc_wall_uro_object_type xml_buffer, uro_ifc_building_furniture_attribute{}.uro_ifc_wall_uro_tag xml_buffer, uro_ifc_building_furniture_attribute{}.uro_ifc_wall_uro_element_type xml_buffer, uro_ifc_building_furniture_attribute{}.uro_ifc_wall_uro_element_type_codeSpace xml_buffer,
      uro_ifc_building_furniture_attribute{}.uro_ifc_wall_uro_predefined_type xml_buffer, uro_ifc_building_furniture_attribute{}.uro_ifc_wall_uro_predefined_type_codeSpace xml_buffer, uro_ifc_building_furniture_attribute{}.uro_ifc_wall_uro_shape_type xml_buffer, uro_ifc_building_furniture_attribute{}.uro_ifc_wall_uro_shape_type_codeSpace xml_buffer, uro_ifc_building_furniture_attribute{}.uro_ifc_wall_uro_number_of_riser xml_int64, uro_ifc_building_furniture_attribute{}.uro_ifc_wall_uro_number_of_treads xml_int64, uro_ifc_building_furniture_attribute{}.uro_ifc_wall_uro_riser_height xml_int64, uro_ifc_building_furniture_attribute{}.uro_ifc_wall_uro_tread_length xml_int64, uro_ifc_building_furniture_attribute{}.uro_ifc_wall_uro_operation_type xml_char(11), uro_ifc_building_furniture_attribute{}.uro_ifc_wall_uro_capacity_by_weight xml_real64, uro_ifc_building_furniture_attribute{}.uro_ifc_wall_uro_capacity_by_weight_units xml_buffer, uro_ifc_building_furniture_attribute{}.uro_ifc_wall_uro_capacity_by_number xml_int64, uro_ifc_building_furniture_attribute{}.uro_ifc_wall_uro_nominal_length xml_real64, uro_ifc_building_furniture_attribute{}.uro_ifc_wall_uro_nominal_length_units xml_buffer, uro_ifc_building_furniture_attribute{}.uro_ifc_wall_uro_nominal_width xml_real64, uro_ifc_building_furniture_attribute{}.uro_ifc_wall_uro_nominal_width_units xml_buffer, uro_ifc_building_furniture_attribute{}.uro_ifc_wall_uro_nominal_height xml_real64, uro_ifc_building_furniture_attribute{}.uro_ifc_wall_uro_nominal_height_units xml_buffer, uro_ifc_building_furniture_attribute{}.uro_ifc_wall_uro_gross_foot_print_area xml_real64, uro_ifc_building_furniture_attribute{}.uro_ifc_wall_uro_gross_foot_print_area_units xml_buffer, uro_ifc_building_furniture_attribute{}.uro_ifc_wall_uro_net_foot_print_area xml_real64, uro_ifc_building_furniture_attribute{}.uro_ifc_wall_uro_net_foot_print_area_units xml_buffer, uro_ifc_building_furniture_attribute{}.uro_ifc_wall_uro_gross_side_area xml_real64, uro_ifc_building_furniture_attribute{}.uro_ifc_wall_uro_gross_side_area_units xml_buffer, uro_ifc_building_furniture_attribute{}.uro_ifc_wall_uro_net_side_area xml_real64, uro_ifc_building_furniture_attribute{}.uro_ifc_wall_uro_net_side_area_units xml_buffer, uro_ifc_building_furniture_attribute{}.uro_ifc_wall_uro_gross_side_area_left xml_real64, uro_ifc_building_furniture_attribute{}.uro_ifc_wall_uro_gross_side_area_left_units xml_buffer, uro_ifc_building_furniture_attribute{}.uro_ifc_wall_uro_net_side_area_left xml_real64, uro_ifc_building_furniture_attribute{}.uro_ifc_wall_uro_net_side_area_left_units xml_buffer,
      uro_ifc_building_furniture_attribute{}.uro_ifc_wall_uro_gross_side_area_right xml_real64, uro_ifc_building_furniture_attribute{}.uro_ifc_wall_uro_gross_side_area_right_units xml_buffer, uro_ifc_building_furniture_attribute{}.uro_ifc_wall_uro_net_side_area_right xml_real64, uro_ifc_building_furniture_attribute{}.uro_ifc_wall_uro_net_side_area_right_units xml_buffer, uro_ifc_building_furniture_attribute{}.uro_ifc_wall_uro_gross_volume xml_real64, uro_ifc_building_furniture_attribute{}.uro_ifc_wall_uro_gross_volume_units xml_buffer, uro_ifc_building_furniture_attribute{}.uro_ifc_wall_uro_net_volume xml_real64, uro_ifc_building_furniture_attribute{}.uro_ifc_wall_uro_net_volume_units xml_buffer, uro_ifc_building_furniture_attribute{}.uro_ifc_wall_standard_case_uro_global_id xml_buffer, uro_ifc_building_furniture_attribute{}.uro_ifc_wall_standard_case_uro_name xml_buffer, uro_ifc_building_furniture_attribute{}.uro_ifc_wall_standard_case_uro_description xml_buffer, uro_ifc_building_furniture_attribute{}.uro_ifc_wall_standard_case_uro_object_type xml_buffer, uro_ifc_building_furniture_attribute{}.uro_ifc_wall_standard_case_uro_tag xml_buffer, uro_ifc_building_furniture_attribute{}.uro_ifc_wall_standard_case_uro_element_type xml_buffer, uro_ifc_building_furniture_attribute{}.uro_ifc_wall_standard_case_uro_element_type_codeSpace xml_buffer, uro_ifc_building_furniture_attribute{}.uro_ifc_wall_standard_case_uro_predefined_type xml_buffer, uro_ifc_building_furniture_attribute{}.uro_ifc_wall_standard_case_uro_predefined_type_codeSpace xml_buffer, uro_ifc_building_furniture_attribute{}.uro_ifc_wall_standard_case_uro_shape_type xml_buffer, uro_ifc_building_furniture_attribute{}.uro_ifc_wall_standard_case_uro_shape_type_codeSpace xml_buffer, uro_ifc_building_furniture_attribute{}.uro_ifc_wall_standard_case_uro_number_of_riser xml_int64, uro_ifc_building_furniture_attribute{}.uro_ifc_wall_standard_case_uro_number_of_treads xml_int64, uro_ifc_building_furniture_attribute{}.uro_ifc_wall_standard_case_uro_riser_height xml_int64, uro_ifc_building_furniture_attribute{}.uro_ifc_wall_standard_case_uro_tread_length xml_int64, uro_ifc_building_furniture_attribute{}.uro_ifc_wall_standard_case_uro_operation_type xml_char(11), uro_ifc_building_furniture_attribute{}.uro_ifc_wall_standard_case_uro_capacity_by_weight xml_real64, uro_ifc_building_furniture_attribute{}.uro_ifc_wall_standard_case_uro_capacity_by_weight_units xml_buffer, uro_ifc_building_furniture_attribute{}.uro_ifc_wall_standard_case_uro_capacity_by_number xml_int64, uro_ifc_building_furniture_attribute{}.uro_ifc_wall_standard_case_uro_nominal_length xml_real64, uro_ifc_building_furniture_attribute{}.uro_ifc_wall_standard_case_uro_nominal_length_units xml_buffer, uro_ifc_building_furniture_attribute{}.uro_ifc_wall_standard_case_uro_nominal_width xml_real64,
      uro_ifc_building_furniture_attribute{}.uro_ifc_wall_standard_case_uro_nominal_width_units xml_buffer, uro_ifc_building_furniture_attribute{}.uro_ifc_wall_standard_case_uro_nominal_height xml_real64, uro_ifc_building_furniture_attribute{}.uro_ifc_wall_standard_case_uro_nominal_height_units xml_buffer, uro_ifc_building_furniture_attribute{}.uro_ifc_wall_standard_case_uro_gross_foot_print_area xml_real64, uro_ifc_building_furniture_attribute{}.uro_ifc_wall_standard_case_uro_gross_foot_print_area_units xml_buffer, uro_ifc_building_furniture_attribute{}.uro_ifc_wall_standard_case_uro_net_foot_print_area xml_real64, uro_ifc_building_furniture_attribute{}.uro_ifc_wall_standard_case_uro_net_foot_print_area_units xml_buffer, uro_ifc_building_furniture_attribute{}.uro_ifc_wall_standard_case_uro_gross_side_area xml_real64, uro_ifc_building_furniture_attribute{}.uro_ifc_wall_standard_case_uro_gross_side_area_units xml_buffer, uro_ifc_building_furniture_attribute{}.uro_ifc_wall_standard_case_uro_net_side_area xml_real64, uro_ifc_building_furniture_attribute{}.uro_ifc_wall_standard_case_uro_net_side_area_units xml_buffer, uro_ifc_building_furniture_attribute{}.uro_ifc_wall_standard_case_uro_gross_side_area_left xml_real64, uro_ifc_building_furniture_attribute{}.uro_ifc_wall_standard_case_uro_gross_side_area_left_units xml_buffer, uro_ifc_building_furniture_attribute{}.uro_ifc_wall_standard_case_uro_net_side_area_left xml_real64, uro_ifc_building_furniture_attribute{}.uro_ifc_wall_standard_case_uro_net_side_area_left_units xml_buffer, uro_ifc_building_furniture_attribute{}.uro_ifc_wall_standard_case_uro_gross_side_area_right xml_real64, uro_ifc_building_furniture_attribute{}.uro_ifc_wall_standard_case_uro_gross_side_area_right_units xml_buffer, uro_ifc_building_furniture_attribute{}.uro_ifc_wall_standard_case_uro_net_side_area_right xml_real64, uro_ifc_building_furniture_attribute{}.uro_ifc_wall_standard_case_uro_net_side_area_right_units xml_buffer, uro_ifc_building_furniture_attribute{}.uro_ifc_wall_standard_case_uro_gross_volume xml_real64, uro_ifc_building_furniture_attribute{}.uro_ifc_wall_standard_case_uro_gross_volume_units xml_buffer, uro_ifc_building_furniture_attribute{}.uro_ifc_wall_standard_case_uro_net_volume xml_real64, uro_ifc_building_furniture_attribute{}.uro_ifc_wall_standard_case_uro_net_volume_units xml_buffer, uro_ifc_building_furniture_attribute{}.uro_ifc_window_uro_global_id xml_buffer, uro_ifc_building_furniture_attribute{}.uro_ifc_window_uro_name xml_buffer, uro_ifc_building_furniture_attribute{}.uro_ifc_window_uro_description xml_buffer, uro_ifc_building_furniture_attribute{}.uro_ifc_window_uro_object_type xml_buffer, uro_ifc_building_furniture_attribute{}.uro_ifc_window_uro_tag xml_buffer, uro_ifc_building_furniture_attribute{}.uro_ifc_window_uro_element_type xml_buffer, uro_ifc_building_furniture_attribute{}.uro_ifc_window_uro_element_type_codeSpace xml_buffer,
      uro_ifc_building_furniture_attribute{}.uro_ifc_window_uro_predefined_type xml_buffer, uro_ifc_building_furniture_attribute{}.uro_ifc_window_uro_predefined_type_codeSpace xml_buffer, uro_ifc_building_furniture_attribute{}.uro_ifc_window_uro_shape_type xml_buffer, uro_ifc_building_furniture_attribute{}.uro_ifc_window_uro_shape_type_codeSpace xml_buffer, uro_ifc_building_furniture_attribute{}.uro_ifc_window_uro_number_of_riser xml_int64, uro_ifc_building_furniture_attribute{}.uro_ifc_window_uro_number_of_treads xml_int64, uro_ifc_building_furniture_attribute{}.uro_ifc_window_uro_riser_height xml_int64, uro_ifc_building_furniture_attribute{}.uro_ifc_window_uro_tread_length xml_int64, uro_ifc_building_furniture_attribute{}.uro_ifc_window_uro_operation_type xml_char(11), uro_ifc_building_furniture_attribute{}.uro_ifc_window_uro_capacity_by_weight xml_real64, uro_ifc_building_furniture_attribute{}.uro_ifc_window_uro_capacity_by_weight_units xml_buffer, uro_ifc_building_furniture_attribute{}.uro_ifc_window_uro_capacity_by_number xml_int64, uro_ifc_building_furniture_attribute{}.uro_ifc_window_uro_overall_height xml_real64, uro_ifc_building_furniture_attribute{}.uro_ifc_window_uro_overall_height_units xml_buffer, uro_ifc_building_furniture_attribute{}.uro_ifc_window_uro_overall_width xml_real64, uro_ifc_building_furniture_attribute{}.uro_ifc_window_uro_overall_width_units xml_buffer
Note: v4 / BuildintElementProxy, IfcTransportElement / -> / IntBuildingIstallation, BuildingInstrallation
Note: v7 FME 2022.1.3 / IfcRampFlight, IfcBeam / -> / IntBuildingInstallation or BuildingInstallation / IfcRoof, IfcRoofの子のIfcSlab / -> / Roof
FeatureTypeFilter_2
    ATTRIBUTES = IfcProject,IfcSite,IfcBuilding,IfcBuildingStorey,<Blank>,<Unfiltered>
Terminator
    MESSAGE = Translation Terminated

Bookmark: 位置合わせ・座標系設定パラメーター取得, _reprojection_params に集約 (Matunalモード用)
Tester_8
    BOOL_OP = COMPOSITE
    COMPOSITE_TEST = 1 AND 2 AND 3 AND 4 AND 5 AND 6 AND 7 AND 8
    TEST_CLAUSE:
      TEST @Value(_lengthunit) TYPE NUM
      CASE_INSENSITIVE_TEST @Value(ProjectedCRS.Name) CONTAINS ^EPSG:\d+$
      TEST @Value(MapConversion.Eastings) TYPE NUM
      TEST @Value(MapConversion.Northings) TYPE NUM
      TEST @Value(MapConversion.OrthogonalHeight) TYPE NUM
      TEST @Value(MapConversion.XAxisAbscissa) TYPE NUM
      TEST @Value(MapConversion.XAxisOrdinate) TYPE NUM
      TEST @Value(MapConversion.Scale) TYPE NUM
    TEST_MODE = PER_TEST
    PASSED -> JSONTemplater [ROOT]
    FAILED -> AttributeManager_17
JSONTemplater
    RESULT_ATTRIBUTE = _reprojection_params
    ROOT_QUERY_EXPR:
      {
          "lengthunit" : fme:get-attribute("_lengthunit"),
          "ProjectedCRS" : {
              "Name" : fme:get-attribute("ProjectedCRS.Name")
          },
          "MapConversion" : {
              "Eastings" : xs:double(fme:get-attribute("MapConversion.Eastings")),
              "Northings" : xs:double(fme:get-attribute("MapConversion.Northings")),
              "OrthogonalHeight" : xs:double(fme:get-attribute("MapConversion.OrthogonalHeight")),
              "XAxisAbscissa" : xs:double(fme:get-attribute("MapConversion.XAxisAbscissa")),
              "XAxisOrdinate" : xs:double(fme:get-attribute("MapConversion.XAxisOrdinate")),
              "Scale" : xs:double(fme:get-attribute("MapConversion.Scale"))
          }
      }
    VISIBLE_QUERY_VALIDATE = Yes
    -> AttributeCreator_17
AttributeCreator_17
    ATTR_TABLE:
      SET_TO _lengthmultiplier = FME_CONDITIONAL:DEFAULT_VALUE'1'BOOL_OP;OR;COMPOSITE_TEST;1;TEST @Value(_lengthunit) IN millimetre,millimeter'0.001'FME_NUM_CONDITIONS2___
      SET_TO _coordinate_precision = FME_CONDITIONAL:DEFAULT_VALUE'4'BOOL_OP;OR;COMPOSITE_TEST;1;TEST @Value(_lengthunit) IN millimetre,millimeter'1'FME_NUM_CONDITIONS2___
    -> AttributeManager_17

Bookmark: IfcProject フィーチャーから長さの単位 lengthunits を抽出し全てのフィーチャーに _lengthunits 属性を付与
CoordinateSystemRemover
    -> AttributeRemover
AttributeRemover
    REMOVE_ATTRS = _reprojection_params,_lengthunit
    -> FeatureTypeFilter_6
Note: _lengthmultiplier / mm : 0.001 / m : 1 / _coordinate_precision / mm : 1 / m : 4
FeatureTypeFilter_6
    ATTRIBUTES = <Unfiltered>,IfcProject,<Blank>
    <UNFILTERED> -> FeatureMerger_6 [REQUESTOR]
    IfcProject -> AttributeExposer
AttributeExposer
    ATTR_LIST = lengthunit
    -> AttributeManager_19
AttributeManager_19
    ATTR_TABLE:
      RENAME_SET_VALUE lengthunit > _lengthunit
      SET_TO _lengthmultiplier = FME_CONDITIONAL:DEFAULT_VALUE'1'BOOL_OP;OR;COMPOSITE_TEST;1;TEST @Value(_lengthunit) IN millimetre,millimiter'0.001'FME_NUM_CONDITIONS2___
      SET_TO _coordinate_precision = FME_CONDITIONAL:DEFAULT_VALUE'4'BOOL_OP;OR;COMPOSITE_TEST;1;TEST @Value(_lengthunit) IN millimetre,millimiter'1'FME_NUM_CONDITIONS2___
    -> Junction_37
    -> AttributeKeeper_2
AttributeKeeper_2
    CREATE_BULK_MODE_FEATURES = NO
    KEEP_ATTRS = _lengthunit,_coordinate_precision,_lengthmultiplier
    -> FeatureMerger_6 [SUPPLIER]
FeatureMerger_6
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Junction_68

Bookmark: 全フィーチャーに所属先の階 (storey) のID (_storey_id) とインデクス (_storey_index), 親要素のフィーチャータイプ (_parent_feature_type) を付与
GeometryCoercer
    GQUERY:
      for $geom in //geometry
      where $geom/@fme_geometry_type = 'IFMEExtrusion'
      return number($geom/@fme_id)
    KIND = fme_brep_solid
    COERCED -> Junction_3
    UNTOUCHED -> Junction_3
Junction_3
    -> FeatureMerger [REQUESTOR]
XMLTemplater
    CONSECUTIVE_GROUPS = Yes
    GROUP_BY = _building_id
    OUTPUT_XML_HEADER = Yes
    RESULT_ATTRIBUTE = _result
    ROOT_QUERY_EXPR:
      <ifcFeature
          type="{fme:get-attribute("fme_feature_type")}"
          name="{fme:get-attribute("Name")}"
          id="{fme:get-attribute("ifc_unique_id")}">{
          fme:process-features("SUB", "ifc_parent_unique_id", fme:get-attribute("ifc_unique_id"))
      }</ifcFeature>
    SUB_QUERY_EXPR:
      <ifcFeature
          type="{fme:get-attribute("fme_feature_type")}"
          name="{fme:get-attribute("Name")}"
          id="{fme:get-attribute("ifc_unique_id")}">{
          fme:process-features("SUB", "ifc_parent_unique_id", fme:get-attribute("ifc_unique_id"))
      }</ifcFeature>
    VISIBLE_QUERY_VALIDATE = Yes
    -> PythonCaller
PythonCaller
    GROUP_BY = _building_id
    HIDE_ATTRIBUTES = _result
    NEW_ATTRIBUTES = _storey_id _storey_name _parent_feature_type
    PYTHONSOURCE:
      import fme
      import fmeobjects
      import xml.etree.ElementTree as ET

      class FeatureProcessor(object):
          def __init__(self):
              pass

          def input(self, feature):
              rt = ET.fromstring(feature.getAttribute('_result'))
              parent_map = {c : p for p in rt.iter() for c in p}
              for s in rt.findall('.//ifcFeature[@type="IfcBuildingStorey"]'):
                  attrib = {
                      '_storey_id' : s.get('id'),
                      '_storey_name': s.get('name'),
                  }
                  for d in s.findall('.//ifcFeature'):
                      attrib.update({
                          'ifc_unique_id' : d.get('id'),
                          'fme_feature_type' : d.get('type'),
                          '_parent_feature_type' : parent_map[d].get('type'),
                      })
                      '''
                      attrib['ifc_unique_id'] = d.get('id')
                      attrib['fme_feature_type'] = d.get('type')
                      attrib['_parent_feature_type'] = parent_map[d].get('type')
                      '''
                      feat = fmeobjects.FMEFeature()
                      for k, v in attrib.items():
                          feat.setAttribute(k, v)
                      self.pyoutput(feat)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> FeatureMerger_8 [REQUESTOR]
FeatureMerger_8
    ATTR_ACCUM_MODE = Merge Supplier
    ATTR_CONFLICT_RES = Use Requestor
    IGNORE_NULLS = No
    JOIN_KEYS = @Value(_storey_id) @Value(_storey_id) AUTO
    MERGE_TYPE = Attributes Only
    PROCESS_DUPS = NO
    REJECT_NULL_MISSING_KEYS = No
    SUPPLIERS_FIRST = No
    MERGED -> FeatureMerger [SUPPLIER]
FeatureMerger
    ATTR_ACCUM_MODE = Merge Supplier
    ATTR_CONFLICT_RES = Use Requestor
    GROUP_BY = _building_id
    IGNORE_NULLS = No
    JOIN_KEYS = @Value(ifc_unique_id) @Value(ifc_unique_id) AUTO
    MERGE_TYPE = Attributes Only
    PROCESS_DUPS = NO
    REJECT_NULL_MISSING_KEYS = No
    SUPPLIERS_FIRST = No
    MERGED -> CoordinateRounder
    UNMERGED_REQUESTOR -> FeatureTypeFilter_2

Bookmark: _storey_index (Elevation 昇順, 1-based) 設定
Tester_11
    BOOL_OP = OR
    TEST_CLAUSE = TEST @Value(_ifc_feature_type) = IfcBuildingStorey
    TEST_MODE = TEST
    PASSED -> Sorter_2
Sorter_2
    GROUP_BY = _building_id
    SORT_PARM = Elevation NUMERIC ASCENDING
    SORTED -> Counter_4
Counter_4
    CNT_ATTR = _storey_index
    GROUP_BY = _building_id
    SCOPE = Local
    START = 1
    -> AttributeManager_23
AttributeManager_23
    ATTR_TABLE:
      REMOVE gml_description
      REMOVE gml_name
      REMOVE GlobalId
      REMOVE Name
      REMOVE ObjectType
      REMOVE LongName
      REMOVE CompositionType
      REMOVE Elevation
      REMOVE ElevationWithFlooring
      REMOVE InteriorOrExteriorSpace
      REMOVE LandTitleNumber
      REMOVE NumberOfRiser
      REMOVE NumberOfTreads
      REMOVE OverallHeight
      REMOVE OverallWidth
      REMOVE Tag
      REMOVE ifc_parent_unique_id
      RENAME_SET_VALUE ifc_unique_id > _storey_id
      REMOVE ApplicableOccurrence
      REMOVE ElementType
      REMOVE ifc_type_name
      REMOVE ifc_type_object_id
      REMOVE _lengthunit
      REMOVE _reprojection_params
      REMOVE _ifc_feature_type
      REMOVE _lengthmultiplier
      REMOVE _coordinate_precision
      REMOVE fme_feature_type
    -> FeatureMerger_8 [SUPPLIER]

Bookmark: OpeningElement ソリッド抽出
Deaggregator_5
    ATTR_ACCUM_MODE = Merge List Attributes
    ATTR_CONFLICT_RES = Use List Attribute Values
    EXPLODE_INSTANCES = No
    LIST_ATTR_MODE_LOOKUP = LEAN
    MODE = Flatten One Level
    SPLIT_COMPOSITES = No
    DEAGGREGATED -> GeometryFilter_6
GeometryFilter_6
    FILTER_MODE = SIMPLE
    FILTER_MULTI = FILTER_TYPES]Solid]FME_CONTROLLER_QUERY_FILE]]FME_CONTROLLER_CHOICE]Simple
    Solid -> FeatureMerger_7 [REQUESTOR]

Bookmark: IfcSlab ソリッド
Junction_59
    -> Clipper_3 [CLIPPER]
Deaggregator_3
    ATTR_ACCUM_MODE = Merge List Attributes
    ATTR_CONFLICT_RES = Use List Attribute Values
    EXPLODE_INSTANCES = Yes
    GEOM_NAME_FIELD = _geometry_name
    LIST_ATTR_MODE_LOOKUP = LEAN
    MODE = Flatten One Level
    PART_NUMBER_FIELD = _part_number
    SPLIT_COMPOSITES = No
    DEAGGREGATED -> GeometryFilter_4
GeometryFilter_4
    FILTER_MODE = SIMPLE
    FILTER_MULTI = FILTER_TYPES]Solid]FME_CONTROLLER_QUERY_FILE]]FME_CONTROLLER_CHOICE]Simple
    Solid -> Clipper_3 [CANDIDATE]
    Solid -> Junction_74
Note: Slab から開口部を控除
Clipper_3
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> Junction_22

Bookmark: 壁ソリッド
Deaggregator
    EXPLODE_INSTANCES = Yes
    GEOM_NAME_FIELD = _geometry_name
    LIST_ATTR_MODE_LOOKUP = LEAN
    MODE = Flatten All Levels
    SPLIT_COMPOSITES = No
    DEAGGREGATED -> GeometryFilter
GeometryFilter
    FILTER_MODE = SIMPLE
    FILTER_MULTI = FILTER_TYPES]Solid]FME_CONTROLLER_QUERY_FILE]]FME_CONTROLLER_CHOICE]Simple
    Solid -> Junction_4
    Solid -> w1
    Solid -> SharedItemIDExtractor

Bookmark: 共有アイテム (アピアランス) IDをグローバル変数に格納
SharedItemIDExtractor
    REFERENCE_ATTRIBUTE = _shared_item_id
    SHARED_TYPE = Appearance
    SIDE_TO_EXTRACT = Front Side
    STORAGE_MODE = Attribute
    -> VariableSetter
    <REJECTED> -> Junction_35
VariableSetter
    SCOPE = Local
    VALUE = @Value(_shared_item_id.front{0})
    VARNAME = vSharedItemId_@Value(_building_id)_@Value(ifc_unique_id)
    -> Junction_35
Junction_35
    -> GeometryValidator

Bookmark: 「壁」ソリッドの各面を抽出 -> 法線ベクトル計算 -> 上下の面を除外 -> ジオメトリを属性として保存 -> フットプリントに変換
GeometryValidator
    ISSUE_ATTR_NAME = _issues
    PRESETS = Custom
    REPAIR = Yes
    RULES = CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D PLANAR_SURFACE CHECK_AREA]DO_NOT_CHECK_AREA]TOLERANCE_MODE]AUTO]TOLERANCE]<Unused>]ANGULAR_TOLERANCE_MODE]Automatic]ANGULAR_TOLERANCE]0.0]FME_CONTROLLER_QUERY_FILE]transformers/dependencies/geometryvalidator8/PLANAR_SURFACE.fme]FME_CONTROLLER_CHOICE]PLANAR_SURFACE
    SUMMARY = Detailed
    PASSED -> GeometryPartExtractor_2
    REPAIRED -> GeometryPartExtractor_2
GeometryPartExtractor_2
    GQUERY:
      for $geom in //geometry
      where $geom/@fme_geometry_type = 'IFMEFace'
      return number($geom/@fme_id)
    EXTRACTED -> GeometryValidator_2
GeometryValidator_2
    ISSUE_ATTR_NAME = _issues
    PRESETS = Custom
    REPAIR = No
    RULES = TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> PlanarityFilter
PlanarityFilter
    ANGULAR_TOLERANCE_CHOICE = Automatic
    OUTPUT_NORMAL = Yes
    THICKNESS_TOLERANCE_CHOICE = Automatic
    PLANAR -> AttributeRounder_2
AttributeRounder_2
    PLACES = 3
    ROUND_TYPE = Nearest
    SRC_ATTRS = _surfaceNormalX _surfaceNormalY _surfaceNormalZ
    -> Tester_4
Tester_4
    BOOL_OP = OR
    TEST_CLAUSE = TEST @Evaluate(@abs(@Value(_surfaceNormalZ))) != 1
    TEST_MODE = TEST
    PASSED -> GeometryExtractor
    PASSED -> w2
GeometryExtractor
    ATTR = _geometry
    KIND_LONG = FME Binary
    REMOVE_GEOMETRY = No
    -> SurfaceFootprintReplacer_2
SurfaceFootprintReplacer_2
    OFFSET_Z = 0
    SHADOW_MODE = Overhead Shadow
    FOOTPRINT -> SpatialFilter [Candidate]
    FOOTPRINT -> w3

Bookmark: ソリッドの個別の面を抽出
GeometryPartExtractor_7
    GQUERY:
      for $geom in //geometry
      where $geom/@fme_geometry_type = 'IFMEFace'
      return number($geom/@fme_id)
    EXTRACTED -> SurfaceSplitter_2
GeometryPartExtractor_4
    GQUERY:
      for $geom in //geometry
      where $geom/@fme_geometry_type = 'IFMEFace'
      return number($geom/@fme_id)
    EXTRACTED -> SurfaceSplitter_2

Bookmark: Slab 開口部を示すソリッド作成 -> Ceiling, Floor の開口部境界面 (ClosureSurface) 抽出に使用
Note: 面を抽出
GeometryPartExtractor_10
    GQUERY:
      for $geom in //geometry
      where $geom/@fme_geometry_type = 'IFMEFace'
      return number($geom/@fme_id)
    EXTRACTED -> BoundsExtractor_3
BoundsExtractor_3
    ZMAX = _zmax
    ZMIN = _zmin
    -> PlanarityFilter_4
Note: 法線ベクトル計算
PlanarityFilter_4
    ANGULAR_TOLERANCE = 20
    ANGULAR_TOLERANCE_CHOICE = Custom
    OUTPUT_NORMAL = Yes
    THICKNESS_TOLERANCE = 0.005/@Value(_lengthmultiplier)
    THICKNESS_TOLERANCE_CHOICE = Custom
    PLANAR -> Tester_12
Note: 上面のみ抽出
Tester_12
    BOOL_OP = OR
    TEST_CLAUSE = TEST 0.5 < @Value(_surfaceNormalZ)
    TEST_MODE = TEST
    PASSED -> AttributeManager_24
AttributeManager_24
    ATTR_TABLE:
      REMOVE gml_description
      REMOVE gml_name
      REMOVE GlobalId
      REMOVE Name
      REMOVE ObjectType
      REMOVE LongName
      REMOVE CompositionType
      REMOVE Elevation
      REMOVE ElevationWithFlooring
      REMOVE InteriorOrExteriorSpace
      REMOVE LandTitleNumber
      REMOVE NumberOfRiser
      REMOVE NumberOfTreads
      REMOVE OverallHeight
      REMOVE OverallWidth
      REMOVE Tag
      REMOVE ifc_parent_unique_id
      REMOVE ifc_unique_id
      REMOVE ApplicableOccurrence
      REMOVE ElementType
      REMOVE ifc_type_name
      REMOVE ifc_type_object_id
      REMOVE _lengthunit
      REMOVE _reprojection_params
      REMOVE _ifc_feature_type
      REMOVE _coordinate_precision
      REMOVE fme_feature_type
      REMOVE fme_basename
      REMOVE Description
      REMOVE _storey_id
      REMOVE _storey_name
      REMOVE _parent_feature_type
      REMOVE _part_number
      REMOVE _geometry_name
      REMOVE _surfaceNormalX
      REMOVE _surfaceNormalY
      REMOVE _surfaceNormalZ
      REMOVE _pointOnSurfaceX
      REMOVE _pointOnSurfaceY
      REMOVE _pointOnSurfaceZ
    -> 2DForcer_2
2DForcer_2
    2D -> Sorter_3
Sorter_3
    GROUP_BY = _building_id
    SORT_PARM = _storey_index NUMERIC ASCENDING
    SORTED -> Bufferer_2
Bufferer_2
    ANGLE = 22.5
    CAP_STYLE = Arc
    CORNER_STYLE = Miter
    GROUP_BY = _storey_index _building_id
    MITER_LIMIT = 2
    MODE = AREA
    OFFSET = 0.249/@Value(_lengthmultiplier)
    OFFSET_UNITS = NONE
    PRECISION = APPROX
    BUFFERED -> Bufferer_3
Bufferer_3
    ANGLE = 22.5
    CAP_STYLE = Arc
    CORNER_STYLE = Miter
    MITER_LIMIT = 2
    MODE = AREA
    OFFSET = -0.249/@Value(_lengthmultiplier)
    OFFSET_UNITS = NONE
    PRECISION = APPROX
    BUFFERED -> DonutHoleExtractor_2
DonutHoleExtractor_2
    DEAGGREGATE_INPUT = Yes
    HOLE -> 3DForcer
3DForcer
    KEEPZVAL = No
    ZVALATTR = @Value(_zmin)-2/@Value(_lengthmultiplier)
    -> Extruder_2
Extruder_2
    DIRECTION = Vertical
    DISTANCE = (@Value(_zmax)-@Value(_zmin)) + 4/@Value(_lengthmultiplier)
    EXTRUDED -> ExpressionEvaluator
    EXTRUDED -> Junction_76
ExpressionEvaluator
    ACTION = Overwrite Existing Attributes
    ATTRLIST = _storey_index
    EXPRESSION = @CurrentAttribute()-1
    -> Junction_67
Note: Clipper_5 : Clipper / ひとつ下の階の Ceiling クリップ
Junction_67
    -> Junction_73
Note: Clipper_6 : Clipper / 当該階の Floor クリップ
Junction_76
    -> Junction_77

Bookmark: Slab 開口部による Ceiling と Floor のクリップ
Note: ExpressionEvaluator : Output
Junction_73
    -> Clipper_5 [CLIPPER]
Note: Extruder_2 : Extruded
Junction_77
    -> Clipper_6 [CLIPPER]
Clipper_5
    BOUNDARY_CASES = INSIDE
    CLEANING_TOLERANCE = Automatic
    CLIPPED_ATTR = _clipped
    CLIPPERS_FIRST = NO
    GENERATE_LIST = NO
    GROUP_BY = _building_id _storey_index
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Junction_79
    OUTSIDE -> Junction_78
Clipper_6
    BOUNDARY_CASES = INSIDE
    CLEANING_TOLERANCE = Automatic
    CLIPPED_ATTR = _clipped
    CLIPPERS_FIRST = NO
    GENERATE_LIST = NO
    GROUP_BY = _building_id _storey_index
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Junction_79
    OUTSIDE -> Junction_78

Bookmark: IfcSpace ソリッド
Deaggregator_2
    ATTR_ACCUM_MODE = Merge List Attributes
    ATTR_CONFLICT_RES = Use List Attribute Values
    EXPLODE_INSTANCES = Yes
    GEOM_NAME_FIELD = _geometry_name
    LIST_ATTR_MODE_LOOKUP = LEAN
    MODE = Flatten One Level
    PART_NUMBER_FIELD = _part_number
    SPLIT_COMPOSITES = No
    DEAGGREGATED -> GeometryFilter_2
GeometryFilter_2
    FILTER_MODE = SIMPLE
    FILTER_MULTI = FILTER_TYPES]Solid]FME_CONTROLLER_QUERY_FILE]]FME_CONTROLLER_CHOICE]Simple
    Solid -> Junction_4
    Solid -> AttributeManager_4
    Solid -> SurfaceFootprintReplacer

Bookmark: 壁と屋内空間をあわせたフットプリント
Aggregator_2
    ACCUM_ATTRS_NAME = Drop Incoming Attributes
    AGGREGATE_TYPE = Homogeneous Collection (If Possible)
    GROUP_BY = _building_id _storey_id
    MODE = Geometry - Assemble One Level
    SEP = ,
    AGGREGATE -> SurfaceFootprintReplacer_6
SurfaceFootprintReplacer_6
    OFFSET_Z = Minimum Z
    SHADOW_MODE = Overhead Shadow
    FOOTPRINT -> m2
    FOOTPRINT -> NeighborFinder [CANDIDATE]
    FOOTPRINT -> FeatureMerger_3 [REQUESTOR]

Bookmark: CurtainlWall, Plateを除く各階オブジェクトの最小,最大Zを求める
Note: 複数階にまたがる可能性のあるCurtainWallを除く
Tester_6
    BOOL_OP = OR
    TEST_CLAUSE = TEST @Value(fme_feature_type) NOT_IN IfcCurtainWall,IfcPlate
    TEST_MODE = TEST
    PASSED -> Aggregator_4
Aggregator_4
    ACCUM_ATTRS_NAME = Drop Incoming Attributes
    AGGREGATE_TYPE = Homogeneous Collection (If Possible)
    GROUP_BY = _building_id _storey_id
    MODE = Geometry - Assemble One Level
    SEP = ,
    AGGREGATE -> BoundsExtractor
BoundsExtractor
    ZMAX = _zmax
    ZMIN = _zmin
    -> FeatureMerger_3 [SUPPLIER]

Bookmark: 壁と屋内空間をあわせた外形ソリッドからスラブソリッドを控除
Extruder
    DIRECTION = Vertical
    DISTANCE = @Value(_zmax)-@Value(_zmin)
    EXTRUDED -> Clipper_4 [CANDIDATE]
Clipper_4
    BOUNDARY_CASES = INSIDE
    CLEANING_TOLERANCE = Automatic
    CLIPPED_ATTR = _clipped
    CLIPPERS_FIRST = NO
    GENERATE_LIST = NO
    GROUP_BY = _building_id _storey_id
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> AttributeKeeper
    <REJECTED> -> Junction_36

Bookmark: 接していない部分のうち、元がスラブだったものを選択
SurfaceOnSurfaceOverlayer
    ACCUM_ATTRS_NAME = Merge Incoming Attributes
    DEAGGREGATE_INPUT = Yes
    ENABLE_TOLERANCE = No
    GROUP_BY = _building_id
    OVC_ATTR = _overlaps
    SURFACE -> Tester_5
    <REJECTED> -> Junction_33
Tester_5
    BOOL_OP = COMPOSITE
    COMPOSITE_TEST = 1 AND 2
    TEST_CLAUSE:
      TEST _storey_id ATTRIBUTE_HAS_A_VALUE ""
      TEST @Value(_overlaps) < 2
    TEST_MODE = TEST
    PASSED -> BoundsExtractor_2
Junction_33

Bookmark: 面の分類
PlanarityFilter_3
    ANGULAR_TOLERANCE_CHOICE = Automatic
    OUTPUT_NORMAL = Yes
    THICKNESS_TOLERANCE_CHOICE = Automatic
    PLANAR -> TestFilter_2
TestFilter_2
    DEFAULT_VALUE = 下向き (Ground)
    PASSED_TEST_GROUP_OUTPUT = FIRST
    TEST_LIST:
      "BOOL_OP,OR,COMPOSITE_TEST,""""""1 OR 2"""""",TEST_CLAUSE,TEST @Value(fme_feature_type) = IfcRoof
      TEST @Value(_parent_feature_type) = IfcRoof",屋根 (Roof),"BOOL_OP,OR,COMPOSITE_TEST,""""""1"""""",TEST_CLAUSE,TEST @Evaluate(@round(@Value(_surfaceNormalZ))) = 0",鉛直 (Wall),"BOOL_OP,OR,COMPOSITE_TEST,""""""1"""""",TEST_CLAUSE,TEST 0 < @Value(_surfaceNormalZ)",上向き (OuterFloor),"BOOL_OP,AND,COMPOSITE_TEST,""""""1 AND 2"""""",TEST_CLAUSE,TEST @Value(_surfaceNormalZ) < 0
      TEST @Value(_zmin.min) < @Value(_zmin)",下向き (OuterCeiling)
    屋根 (Roof) -> AttributeCreator_10
    鉛直 (Wall) -> Junction_28
    上向き (OuterFloor) -> AttributeCreator_11
    下向き (OuterCeiling) -> AttributeCreator_12
    下向き (Ground) -> AttributeCreator_13

Bookmark: 出力先フィーチャータイプ名設定
AttributeCreator_10
    ATTR_TABLE = SET_TO _citygml_feature_type = RoofSurface
    -> AttributeManager_9
AttributeCreator_11
    ATTR_TABLE = SET_TO _citygml_feature_type = OuterFloorSurface
    -> AttributeManager_9
AttributeCreator_12
    ATTR_TABLE = SET_TO _citygml_feature_type = OuterCeilingSurface
    -> AttributeManager_9
AttributeCreator_13
    ATTR_TABLE = SET_TO _citygml_feature_type = GroundSurface
    -> AttributeManager_9

Bookmark: 屋内空間フットプリントを階ごとに融合
SurfaceFootprintReplacer
    OFFSET_Z = 0
    SHADOW_MODE = Overhead Shadow
    FOOTPRINT -> Bufferer_4
Bufferer_4
    ANGLE = 22.5
    CAP_STYLE = Arc
    CORNER_STYLE = Miter
    GROUP_BY = _building_id _storey_id
    MITER_LIMIT = 2
    MODE = AREA
    OFFSET = 500
    OFFSET_UNITS = NONE
    PRECISION = APPROX
    BUFFERED -> Bufferer_5
Bufferer_5
    ANGLE = 22.5
    CAP_STYLE = Arc
    CORNER_STYLE = Miter
    MITER_LIMIT = 2
    MODE = AREA
    OFFSET = -600
    OFFSET_UNITS = NONE
    PRECISION = APPROX
    BUFFERED -> SpatialFilter [Filter]
    BUFFERED -> Junction_41

Bookmark: 壁面のフットプリントが面（斜め壁）の場合、各辺に分解して長い方から2辺を選択
Note: _temp_id
Counter
    CNT_ATTR = _temp_id
    SCOPE = Local
    START = 0
    -> Chopper
Chopper
    DEAGGREGATE_INPUT = Deaggregate
    MAX_VERTICES = 2
    MODE = By Vertex
    REMNANT_ATTR = _remnant
    CHOPPED -> LengthCalculator
LengthCalculator
    DIM = 2
    LEN_ATTR = _length
    MULT = 1
    -> Sorter
Sorter
    GROUP_BY = _building_id _storey_id _temp_id
    SORT_PARM = _length NUMERIC DESCENDING
    SORTED -> Sampler
Sampler
    GROUP_BY = _building_id _storey_id _temp_id
    RATE = 2
    SAMPLE_MODE = No
    SAMPLE_TYPE_LONG = First N Features
    SAMPLED -> Junction_18

Bookmark: Bridge -> Donut, アピアランス復元
Counter_3
    CNT_ATTR = _temp_id
    SCOPE = Local
    START = 0
    -> Triangulator
Triangulator
    DEAGGREGATE_INPUT = Deaggregate
    TIN_SURFACE -> GeometryPartExtractor_5
GeometryPartExtractor_5
    GQUERY:
      for $geom in //geometry
      where $geom/@fme_geometry_type = 'Mesh Part'
      return number($geom/@fme_id)
    EXTRACTED -> SurfaceDissolver_2
SurfaceDissolver_2
    ACCUM_INPUT_ATTRS = Use Attributes From One Feature
    DEAGGREGATE_INPUT = Yes
    GROUP_BY = _temp_id
    MATCHING_APPS = No
    NORMAL_TOLERANCE = 0.01
    OFFSET_TOLERANCE = 0.01
    SEPARATE_SURFACES = No
    SURFACE -> VariableRetriever
VariableRetriever
    SCOPE = Global
    VALUE_ATTR = _shared_item_id
    VARNAME = vSharedItemId_@Value(_building_id)_@Value(ifc_unique_id)
    -> SharedItemIDSetter
SharedItemIDSetter
    GQUERY:
      for $geom in //geometry
      where $geom/count(parent::geometry) = 0
      return number($geom/@fme_id)
    REFERENCE_ATTRIBUTE = _shared_item_id.front{0}
    SHARED_TYPE = Appearance
    SIDE_TO_SET = Front Side
    STORAGE_MODE = From Attribute
    TEXTURE_MAPPING_TYPE_CHOICE = Surface Normal
    TEXTURE_U_REPEAT_FACTOR = 1.0
    TEXTURE_V_REPEAT_FACTOR = 1.0
    USE_EXISTING_TEXTURE_COORDINATES = No
    U_ORIGIN_OFFSET = 0.0
    V_ORIGIN_OFFSET = 0.0
    -> Junction_34
    <REJECTED> -> Junction_34
Junction_34
    -> AttributeManager_8

Bookmark: CompositeSurface -> MultiSurface
GeometryFilter_5
    FILTER_MODE = COMPLETE
    FILTER_MULTI = FILTER_TYPES]CompositeSurface]INSTANCES]INSTANCE]FME_CONTROLLER_QUERY_FILE]]FME_CONTROLLER_CHOICE]Complete
    CompositeSurface -> Deaggregator_4
    <UNFILTERED> -> PLATEAU.IfcReprojector_11 [IfcFeature]
Deaggregator_4
    ATTR_ACCUM_MODE = Merge List Attributes
    ATTR_CONFLICT_RES = Use List Attribute Values
    EXPLODE_INSTANCES = No
    LIST_ATTR_MODE_LOOKUP = LEAN
    MODE = Flatten One Level
    SPLIT_COMPOSITES = Yes
    DEAGGREGATED -> Aggregator_5
Aggregator_5
    ACCUM_ATTRS_NAME = Drop Incoming Attributes
    AGGREGATE_TYPE = Homogeneous Collection (If Possible)
    GROUP_BY = gml_id
    MODE = Geometry - Assemble One Level
    SEP = ,
    AGGREGATE -> PLATEAU.IfcReprojector_11 [IfcFeature]

Bookmark: IfcSpace -> 個別の面を抽出 -> 同一平面上で隣接する面をディゾルブ -> 表裏を逆転 -> 法線ベクトルの方向に基づいて天井、床、屋内壁に分類
GeometryPartExtractor_3
    GQUERY:
      for $geom in //geometry
      where $geom/@fme_geometry_type = 'IFMEFace'
      return number($geom/@fme_id)
    EXTRACTED -> SurfaceDissolver
SurfaceDissolver
    ACCUM_INPUT_ATTRS = Use Attributes From One Feature
    DEAGGREGATE_INPUT = Yes
    GROUP_BY = _building_id _storey_id _room_gml_id
    MATCHING_APPS = No
    NORMAL_TOLERANCE = 1
    OFFSET_TOLERANCE = 1e-4
    SEPARATE_SURFACES = No
    SURFACE -> Orientor_2
Orientor_2
    FLIP_APPEARANCES_CHOICE = Yes
    KIND = REVERSE
    ORIENTED -> PlanarityFilter_2
PlanarityFilter_2
    ANGULAR_TOLERANCE_CHOICE = Automatic
    OUTPUT_NORMAL = Yes
    THICKNESS_TOLERANCE_CHOICE = Automatic
    PLANAR -> AttributeRounder
AttributeRounder
    PLACES = 4
    ROUND_TYPE = Nearest
    SRC_ATTRS = _surfaceNormalX _surfaceNormalY _surfaceNormalZ
    -> AttributeCreator

Bookmark: Bridge -> Donut, アピアランス復元
Triangulator_2
    DEAGGREGATE_INPUT = Deaggregate
    TIN_SURFACE -> GeometryPartExtractor_6
GeometryPartExtractor_6
    GQUERY:
      for $geom in //geometry
      where $geom/@fme_geometry_type = 'Mesh Part'
      return number($geom/@fme_id)
    EXTRACTED -> SurfaceDissolver_3
SurfaceDissolver_3
    ACCUM_INPUT_ATTRS = Use Attributes From One Feature
    DEAGGREGATE_INPUT = Yes
    GROUP_BY = _boundary_gml_id _building_id
    MATCHING_APPS = No
    NORMAL_TOLERANCE = 0.01
    OFFSET_TOLERANCE = 0.01
    SEPARATE_SURFACES = No
    SURFACE -> Aggregator_6
Aggregator_6
    ACCUM_ATTRS_NAME = Use Attributes From One Feature
    AGGREGATE_TYPE = Homogeneous Collection (If Possible)
    GROUP_BY = _boundary_gml_id _building_id
    MODE = Geometry - Assemble One Level
    SEP = ,
    AGGREGATE -> TestFilter

Bookmark: Room ソリッドの作成
GeometryPartExtractor
    GQUERY:
      for $geom in //geometry
      where $geom/@fme_geometry_type = 'IFMEFace'
      return number($geom/@fme_id)
    EXTRACTED -> Aggregator_3
Aggregator_3
    ACCUM_ATTRS_NAME = Use Attributes From One Feature
    AGGREGATE_TYPE = Homogeneous Collection (If Possible)
    GROUP_BY = _building_id _room_gml_id
    MODE = Geometry - Assemble One Level
    SEP = ,
    AGGREGATE -> GeometryCoercer_3
GeometryCoercer_3
    GQUERY:
      for $geom in //geometry
      where $geom/count(parent::geometry) = 0
      return number($geom/@fme_id)
    KIND = fme_brep_solid
    COERCED -> AttributeRenamer

Bookmark: IfcFurnishingElement -> BuildingFurniture 変換（ジオメトリの簡略化を含む）
Note: AttributeManager_14 : Output
Junction_48
    -> FeatureMerger_5 [SUPPLIER]
GeometryRefiner_3
    -> GeometryCoercer_2
Note: BRepSolid を構成する CompositeSurface を一旦 Mesh に変換し、MeshSimplifire によって簡略化したうえで CompositeSurface に戻す。
GeometryCoercer_2
    GQUERY:
      for $geom in //geometry
      where $geom/@fme_geometry_type = 'IFMECompositeSurface'
      return number($geom/@fme_id)
    KIND = fme_mesh
    COERCED -> MeshSimplifier
MeshSimplifier
    AMOUNT = 0.2
    MODE = RELATIVE
    SIMPLIFIED -> GeometryCoercer_4
GeometryCoercer_4
    GQUERY:
      for $geom in //geometry
      where $geom/@fme_geometry_type = 'IFMEMesh'
      return number($geom/@fme_id)
    KIND = fme_composite_surface
    COERCED -> FeatureMerger_5 [REQUESTOR]
Note: 所属先の Room の gml_id を / gml_parent_id として付与。
FeatureMerger_5
    ATTR_ACCUM_MODE = Merge Supplier
    ATTR_CONFLICT_RES = Use Requestor
    IGNORE_NULLS = No
    JOIN_KEYS = @Value(ifc_parent_unique_id) @Value(ifc_parent_unique_id) AUTO
    MERGE_TYPE = Attributes Only
    PROCESS_DUPS = NO
    REJECT_NULL_MISSING_KEYS = No
    SUPPLIERS_FIRST = No
    MERGED -> AttributeManager_15
Note: citygml_feature_role: interiorFurniture / citygml_lod_name: lod4Geometry
AttributeManager_15
    ATTR_TABLE:
      SET_TO gml_id = frntr_@UUID()
      SET_TO citygml_feature_role = interiorFurniture
      SET_TO citygml_lod_name = lod4Geometry
      SET_TO _citygml_feature_type = BuildingFurniture
    -> GeometryPropertySetter_11
GeometryPropertySetter_11
    OVERWRITE_CHOICE = Yes
    REMOVE_ATTRIBUTE = No
    SETTYPE_PARAM = Traits From Attributes
    SRC_ATTRS = citygml_lod_name
    SET -> PLATEAU.IfcReprojector [IfcFeature]

Bookmark: IFCフィーチャータイプと出力先LODによる選別
AttributeFilter_2
    ATTR_NAME = _ifc_feature_type
    ATTR_VALUES = IfcColumn,IfcRamp,IfcRampFlight,IfcStair,IfcStairFlight,IfcBuildingElementProxy,IfcTransportElement,<Unfiltered>,<Empty>,<Missing>,<Null>
    IfcColumn -> Tester_LOD_Greater_Than_4.1
    IfcRamp -> Tester_LOD_Greater_Than_4.0
    IfcRampFlight -> Tester_LOD_Greater_Than_4.0
    IfcStair -> Tester_LOD_Greater_Than_4.0
    IfcStairFlight -> Tester_LOD_Greater_Than_4.0
    IfcBuildingElementProxy -> Tester_LOD_Greater_Than_4.1
    IfcTransportElement -> Tester_LOD_Greater_Than_4.0
    <UNFILTERED> -> Junction_58
Tester_LOD_Greater_Than_4.1
    BOOL_OP = OR
    TEST_CLAUSE = TEST 4.1 < $(DEST_LOD)
    TEST_MODE = TEST
    PASSED -> AttributeCreator_15
Tester_LOD_Greater_Than_4.0
    BOOL_OP = OR
    TEST_CLAUSE = TEST 4.0 < $(DEST_LOD)
    TEST_MODE = TEST
    PASSED -> AttributeCreator_15
Junction_58
    -> Junction_61
Junction_61
    -> AttributeCreator_15

Bookmark: Pending
Address (writer CITYGML_2)
    attributes: citygml_target_uri xml_buffer, citygml_feature_role xml_buffer, citygml_feature_role_attr_name xml_buffer, citygml_feature_role_attr_val xml_buffer, gml_description xml_buffer, gml_name xml_buffer, citygml_address xml_xml
CityObjectGroup (writer CITYGML_2)
    attributes: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

FME custom transformer PLATEAU.IfcReprojector

Parameters:
- REPROJECTION_PARAMS =   # Reprojection Parameters
- LENGTH_MULTIPLIER =   # Length Multiplier
- DEST_COORDSYS =   # Destination Coordinate System

IfcFeature (input)
    -> ParameterFetcher
ParameterFetcher
    ATTR_LIST = __reprojection_params $(REPROJECTION_PARAMS)
    -> Tester
Tester
    BOOL_OP = OR
    TEST_CLAUSE = TEST @Value(__reprojection_params) TYPE JSON
    TEST_MODE = TEST
    PASSED -> JSONFlattener
    FAILED -> Junction_3
JSONFlattener
    ERROR_LIST_ATTR = _json_error
    JSON_DOCUMENT = @Value(__reprojection_params)
    PREFIX_STRING = __
    READ_FROM_FILE = NO
    RECURSIVE = Yes
    -> AttributeExposer
AttributeExposer
    ATTR_LIST = __lengthunit,__MapConversion.Eastings,__MapConversion.Northings,__MapConversion.OrthogonalHeight,__MapConversion.Scale,__MapConversion.XAxisAbscissa,__MapConversion.XAxisOrdinate,__ProjectedCRS.Description,__ProjectedCRS.GeodeticDatum,__ProjectedCRS.MapProjection,__ProjectedCRS.MapZone,__ProjectedCRS.Name,__ProjectedCRS.VerticalDatum
    -> 3DRotator
3DRotator
    ANGLE = @radToDeg(@atan2(@Value(__MapConversion.XAxisOrdinate),@Value(__MapConversion.XAxisAbscissa)))
    AXIS_CHOICE = Z Axis
    ROTATED -> Scaler
Scaler
    RASTER_SCALING = Extents
    SCALE_ORIGIN = 0,0
    TEXT_LOC_ONLY = Location and Size
    XSCALE = @Value(__MapConversion.Scale)
    YSCALE = @Value(__MapConversion.Scale)
    ZSCALE = @Value(__MapConversion.Scale)
    SCALED -> Offsetter
Offsetter
    MODE = Cartesian Coordinate
    XOFF = @Value(__MapConversion.Eastings)
    YOFF = @Value(__MapConversion.Northings)
    ZOFF = @Value(__MapConversion.OrthogonalHeight)
    OFFSET -> Scaler_2
    <REJECTED> -> Junction
Scaler_2
    RASTER_SCALING = Extents
    SCALE_ORIGIN = 0,0
    TEXT_LOC_ONLY = Location and Size
    XSCALE = $(LENGTH_MULTIPLIER)
    YSCALE = $(LENGTH_MULTIPLIER)
    ZSCALE = $(LENGTH_MULTIPLIER)
    SCALED -> CoordinateSystemSetter
CoordinateSystemSetter
    COORDSYS = @Value(__ProjectedCRS.Name)
    -> Tester_3
Tester_3
    BOOL_OP = OR
    TEST_CLAUSE = TEST $(DEST_COORDSYS) != ""
    TEST_MODE = TEST
    PASSED -> CsmapReprojector
    FAILED -> BulkAttributeRemover
CsmapReprojector
    DEST = $(DEST_COORDSYS)
    INTERPOLATION_TYPE_NAME = Nearest Neighbor
    RASTER_CELL_SIZE = Preserve Cells
    RASTER_TOLERANCE = 0.0
    REPROJECTED -> BulkAttributeRemover
Junction
Note: BulkAttributeRemover : Input
Junction_3
    -> Junction_4
Note: Junction_2 : Output
Junction_4
    -> BulkAttributeRemover
BulkAttributeRemover
    ATTR_EXP = ^__.+
    -> Reprojected (output)
Reprojected (output)

FME custom transformer PLATEAU.IfcAttributeExtractor

Input (input)
    -> AttributeExposer
AttributeExposer
    ATTR_LIST = _building_id,ifc_unique_id,ifc_parent_unique_id,gml_description,gml_name,GlobalId,Name,LongName,ObjectType,Tag,OverallHeight,OverallWidth,_ifc_feature_type
    -> TestFilter
TestFilter
    DEFAULT_VALUE = <UNFILTERED>
    PASSED_TEST_GROUP_OUTPUT = ALL
    TEST_LIST = "BOOL_OP,OR,COMPOSITE_TEST,""""""1"""""",TEST_CLAUSE,TEST @Value(_ifc_feature_type) = IfcSpace",Room,"BOOL_OP,OR,COMPOSITE_TEST,""""""1"""""",TEST_CLAUSE,TEST @Value(_ifc_feature_type) IN IfcStair,IfcStairFlight,IfcRamp,IfcRailing,IfcBuildingElementProxy,IfcTransportElement",BuildingInstallation,"BOOL_OP,OR,COMPOSITE_TEST,""""""1"""""",TEST_CLAUSE,TEST @Value(_ifc_feature_type) = IfcWindow",Window,"BOOL_OP,OR,COMPOSITE_TEST,""""""1"""""",TEST_CLAUSE,TEST @Value(_ifc_feature_type) = IfcDoor",Door,"BOOL_OP,OR,COMPOSITE_TEST,""""""1"""""",TEST_CLAUSE,TEST @Value(_ifc_feature_type) = IfcOpeningElement",OpeningElement
    Room -> AttributeManager_18
    Window -> GeometryPartExtractor
    Door -> GeometryPartExtractor_3
    OpeningElement -> GeometryPartExtractor_2
AttributeManager_18
    ATTR_TABLE:
      REMOVE GlobalId
      REMOVE Name
      REMOVE LongName
      REMOVE ObjectType
      REMOVE Tag
      REMOVE OverallHeight
      REMOVE OverallWidth
GeometryRemover
    -> FeatureMerger [REQUESTOR]
GeometryRemover_2
    -> FeatureMerger_2 [REQUESTOR]
GeometryRemover_3
    -> FeatureMerger_2 [SUPPLIER]
    -> FeatureMerger [SUPPLIER]
Note: uro_ifc_opening_attribute{0}.uro_ifc_opening_element_uro_global_id / uro_ifc_opening_attribute{1}.uro_ifc_window_uro_global_id / uro_ifc_opening_attribute{2}.uro_ifc_pset_opening_element_common_uro_reference / uro_ifc_opening_attribute{3}.uro_ifc_pset_window_common_uro_reference / uro_ifc_opening_attribute{0}.uro_ifc_opening_element_uro_global_id / uro_ifc_opening_attribute{1}.uro_ifc_door_uro_global_id / uro_ifc_opening_attribute{2}.uro_ifc_pset_opening_element_common_uro_reference / uro_ifc_opening_attribute{3}.uro_ifc_pset_door_common_uro_reference
FeatureMerger
    ATTR_ACCUM_MODE = Merge Supplier
    ATTR_CONFLICT_RES = Use Requestor
    IGNORE_NULLS = No
    JOIN_KEYS = @Value(ifc_parent_unique_id) @Value(ifc_unique_id) AUTO
    MERGE_TYPE = Attributes Only
    PROCESS_DUPS = NO
    REJECT_NULL_MISSING_KEYS = No
    SUPPLIERS_FIRST = No
    MERGED -> PythonCaller_Window
    UNMERGED_REQUESTOR -> PythonCaller_Window
PythonCaller_Window
    HIDE_ATTRIBUTES = uro_ifc_opening_element_uro_description uro_ifc_opening_element_uro_global_id uro_ifc_opening_element_uro_name uro_ifc_opening_element_uro_object_type uro_ifc_opening_element_uro_tag uro_ifc_pset_opening_element_common_uro_fire_exit uro_ifc_pset_opening_element_common_uro_parallel_jambs uro_ifc_pset_opening_element_common_uro_protected_opening uro_ifc_pset_opening_element_common_uro_purpose uro_ifc_pset_opening_element_common_uro_reference uro_ifc_pset_window_common_uro_acoustic_rating uro_ifc_pset_window_common_uro_firerating uro_ifc_pset_window_common_uro_GlazingAreaFraction uro_ifc_pset_window_common_uro_infiltration uro_ifc_pset_window_common_uro_is_external uro_ifc_pset_window_common_uro_reference uro_ifc_pset_window_common_uro_security_rating uro_ifc_pset_window_common_uro_SmokeStop uro_ifc_pset_window_common_uro_thermal_transmittance uro_ifc_window_uro_description uro_ifc_window_uro_element_type uro_ifc_window_uro_global_id uro_ifc_window_uro_name uro_ifc_window_uro_object_type uro_ifc_window_uro_overall_height uro_ifc_window_uro_overall_height_units uro_ifc_window_uro_overall_width uro_ifc_window_uro_overall_width_units uro_ifc_window_uro_tag
    PYTHONSOURCE:
      import fme
      import fmeobjects, re

      class IfcAttributeSetter_Window(object):
          def __init__(self):
              self.prefix = [
                  'uro_ifc_opening_element_',
                  'uro_ifc_window_',
                  'uro_ifc_pset_opening_element_common_',
                  'uro_ifc_pset_window_common_',
              ]
              self.regex = re.compile('^(%s).+' % '|'.join(self.prefix))

          def input(self, feature):
              prefixToAttrs = {} # {prefix : [attr]}
              for attr in feature.getAllAttributeNames():
                  m = self.regex.match(attr)
                  if m:
                      prefixToAttrs.setdefault(m.group(1), []).append(attr)

              index = 0
              for p in self.prefix:
                  attrNames = prefixToAttrs.get(p, None)
                  if attrNames:
                      prefix = 'uro_ifc_opening_attribute{%d}.' % index
                      index += 1
                      for source in attrNames:
                          target = prefix + source
                          feature.performFunction('@RenameAttributes(%s,%s)' % (target, source))

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = IfcAttributeSetter_Window
    -> Window (output)
Window (output)
FeatureMerger_2
    ATTR_ACCUM_MODE = Merge Supplier
    ATTR_CONFLICT_RES = Use Requestor
    IGNORE_NULLS = No
    JOIN_KEYS = @Value(ifc_parent_unique_id) @Value(ifc_unique_id) AUTO
    MERGE_TYPE = Attributes Only
    PROCESS_DUPS = NO
    REJECT_NULL_MISSING_KEYS = No
    SUPPLIERS_FIRST = No
    MERGED -> PythonCaller_Door
    UNMERGED_REQUESTOR -> PythonCaller_Door
PythonCaller_Door
    HIDE_ATTRIBUTES = uro_ifc_opening_element_uro_description uro_ifc_opening_element_uro_global_id uro_ifc_opening_element_uro_name uro_ifc_opening_element_uro_object_type uro_ifc_opening_element_uro_tag uro_ifc_pset_door_common_uro_acoustic_rating uro_ifc_pset_door_common_uro_fire_exit uro_ifc_pset_door_common_uro_firerating uro_ifc_pset_door_common_uro_glazing_area_fraction uro_ifc_pset_door_common_uro_handicap_accessible uro_ifc_pset_door_common_uro_infiltration uro_ifc_pset_door_common_uro_is_external uro_ifc_pset_door_common_uro_reference uro_ifc_pset_door_common_uro_security_rating uro_ifc_pset_door_common_uro_self_closing uro_ifc_pset_door_common_uro_smoke_stop uro_ifc_pset_door_common_uro_thermal_transmittance uro_ifc_pset_opening_element_common_uro_fire_exit uro_ifc_pset_opening_element_common_uro_parallel_jambs uro_ifc_pset_opening_element_common_uro_protected_opening uro_ifc_pset_opening_element_common_uro_purpose uro_ifc_pset_opening_element_common_uro_reference uro_ifc_door_uro_description uro_ifc_door_uro_element_type uro_ifc_door_uro_global_id uro_ifc_door_uro_name uro_ifc_door_uro_object_type uro_ifc_door_uro_overall_height uro_ifc_door_uro_overall_height_units uro_ifc_door_uro_overall_width uro_ifc_door_uro_overall_width_units uro_ifc_door_uro_tag
    PYTHONSOURCE:
      import fme
      import fmeobjects, re

      class IfcAttributeSetter_Door(object):
          def __init__(self):
              self.prefix = [
                  'uro_ifc_opening_element_',
                  'uro_ifc_door_',
                  'uro_ifc_pset_opening_element_common_',
                  'uro_ifc_pset_door_common_',
              ]
              self.regex = re.compile('^(%s).+' % '|'.join(self.prefix))

          def input(self, feature):
              prefixToAttrs = {} # {prefix : [attr]}
              for attr in feature.getAllAttributeNames():
                  m = self.regex.match(attr)
                  if m:
                      prefixToAttrs.setdefault(m.group(1), []).append(attr)

              index = 0
              for p in self.prefix:
                  attrNames = prefixToAttrs.get(p, None)
                  if attrNames:
                      prefix = 'uro_ifc_opening_attribute{%d}.' % index
                      index += 1
                      for source in attrNames:
                          target = prefix + source
                          feature.performFunction('@RenameAttributes(%s,%s)' % (target, source))

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = IfcAttributeSetter_Door
    -> Door (output)
Door (output)

Bookmark: Pset_WindowCommon プロパティ抽出
GeometryPartExtractor
    GQUERY:
      for $geom in //geometry
      where $geom/@fme_geometry_name = 'Pset_WindowCommon'
      return number($geom/@fme_id)
    EXTRACTED -> GeometryPropertyExtractor
    UNTOUCHED -> AttributeManager_Window
GeometryPropertyExtractor
    EXTRACTTYPE_PARAM = Traits
    GQUERY:
      for $geom in //geometry
      where $geom/count(parent::geometry) = 0
      return number($geom/@fme_id)
    PREFIX_EXTRACTED_TRAITS = Yes
    EXTRACTED -> Aggregator
Aggregator
    ACCUM_ATTRS_NAME = Merge Incoming Attributes
    GROUP_BY = ifc_unique_id
    MODE = Attributes Only
    SEP = ,
    AGGREGATE -> AttributeExposer_2
AttributeExposer_2
    ATTR_LIST = Pset_WindowCommon.Reference,Pset_WindowCommon.FireRating,Pset_WindowCommon.AcousticRating,Pset_WindowCommon.IsExternal,Pset_WindowCommon.SecurityRating,Pset_WindowCommon.Infiltration,Pset_WindowCommon.ThermalTransmittance,Pset_WindowCommon.GlazingAreaFraction,Pset_WindowCommon.SmokeStop
    -> AttributeManager_Window
AttributeManager_Window
    ATTR_TABLE:
      RENAME_SET_VALUE GlobalId > uro_ifc_window_uro_global_id
      RENAME_SET_VALUE Name > uro_ifc_window_uro_name
      SET_TO uro_ifc_window_uro_description = @Value(gml_description)
      RENAME_SET_VALUE ObjectType > uro_ifc_window_uro_object_type
      RENAME_SET_VALUE Tag > uro_ifc_window_uro_tag
      SET_TO uro_ifc_window_uro_element_type = @Value(_ifc_feature_type)
      RENAME_SET_VALUE OverallHeight > uro_ifc_window_uro_overall_height
      SET_TO uro_ifc_window_uro_overall_height_units = FME_CONDITIONAL:DEFAULT_VALUE'_FME_NO_OP_'BOOL_OP;OR;COMPOSITE_TEST;1;TEST @Value(uro_ifc_window_uro_overall_height) TYPE NUM'm'FME_NUM_CONDITIONS2___
      RENAME_SET_VALUE OverallWidth > uro_ifc_window_uro_overall_width
      SET_TO uro_ifc_window_uro_overall_width_units = FME_CONDITIONAL:DEFAULT_VALUE'_FME_NO_OP_'BOOL_OP;OR;COMPOSITE_TEST;1;TEST @Value(uro_ifc_window_uro_overall_width) TYPE NUM'm'FME_NUM_CONDITIONS2___
      REMOVE LongName
      RENAME_SET_VALUE Pset_WindowCommon.Reference > uro_ifc_pset_window_common_uro_reference
      RENAME_SET_VALUE Pset_WindowCommon.AcousticRating > uro_ifc_pset_window_common_uro_acoustic_rating
      RENAME_SET_VALUE Pset_WindowCommon.FireRating > uro_ifc_pset_window_common_uro_firerating
      RENAME_SET_VALUE Pset_WindowCommon.SecurityRating > uro_ifc_pset_window_common_uro_security_rating
      RENAME_SET_VALUE Pset_WindowCommon.IsExternal > uro_ifc_pset_window_common_uro_is_external
      RENAME_SET_VALUE Pset_WindowCommon.Infiltration > uro_ifc_pset_window_common_uro_infiltration
      RENAME_SET_VALUE Pset_WindowCommon.ThermalTransmittance > uro_ifc_pset_window_common_uro_thermal_transmittance
      RENAME_SET_VALUE Pset_WindowCommon.GlazingAreaFraction > uro_ifc_pset_window_common_uro_GlazingAreaFraction
      RENAME_SET_VALUE Pset_WindowCommon.SmokeStop > uro_ifc_pset_window_common_uro_SmokeStop
    -> GeometryRemover

Bookmark: Pset_DoorCommon プロパティ抽出
GeometryPartExtractor_3
    GQUERY:
      for $geom in //geometry
      where $geom/@fme_geometry_name = 'Pset_DoorCommon'
      return number($geom/@fme_id)
    EXTRACTED -> GeometryPropertyExtractor_3
    UNTOUCHED -> AttributeManager_Door
GeometryPropertyExtractor_3
    EXTRACTTYPE_PARAM = Traits
    GQUERY:
      for $geom in //geometry
      where $geom/count(parent::geometry) = 0
      return number($geom/@fme_id)
    PREFIX_EXTRACTED_TRAITS = Yes
    EXTRACTED -> Aggregator_2
Aggregator_2
    ACCUM_ATTRS_NAME = Merge Incoming Attributes
    GROUP_BY = ifc_unique_id
    MODE = Attributes Only
    SEP = ,
    AGGREGATE -> AttributeExposer_4
AttributeExposer_4
    ATTR_LIST = Pset_DoorCommon.Reference,Pset_DoorCommon.AcousticRating,Pset_DoorCommon.FireRating,Pset_DoorCommon.SecurityRating,Pset_DoorCommon.IsExternal,Pset_DoorCommon.Infiltration,Pset_DoorCommon.ThermalTransmittance,Pset_DoorCommon.GlazingAreaFraction,Pset_DoorCommon.HandicapAccessible,Pset_DoorCommon.FireExit,Pset_DoorCommon.SelfClosing,Pset_CoorCommon.SmokeStop
    -> AttributeManager_Door
AttributeManager_Door
    ATTR_TABLE:
      RENAME_SET_VALUE GlobalId > uro_ifc_door_uro_global_id
      RENAME_SET_VALUE Name > uro_ifc_door_uro_name
      SET_TO uro_ifc_door_uro_description = @Value(gml_description)
      RENAME_SET_VALUE ObjectType > uro_ifc_door_uro_object_type
      RENAME_SET_VALUE Tag > uro_ifc_door_uro_tag
      SET_TO uro_ifc_door_uro_element_type = @Value(_ifc_feature_type)
      RENAME_SET_VALUE OverallHeight > uro_ifc_door_uro_overall_height
      SET_TO uro_ifc_door_uro_overall_height_units = FME_CONDITIONAL:DEFAULT_VALUE'_FME_NO_OP_'BOOL_OP;OR;COMPOSITE_TEST;1;TEST @Value(uro_ifc_door_uro_overall_height) TYPE NUM'm'FME_NUM_CONDITIONS2___
      RENAME_SET_VALUE OverallWidth > uro_ifc_door_uro_overall_width
      SET_TO uro_ifc_door_uro_overall_width_units = FME_CONDITIONAL:DEFAULT_VALUE'_FME_NO_OP_'BOOL_OP;OR;COMPOSITE_TEST;1;TEST @Value(uro_ifc_door_uro_overall_width) TYPE NUM'm'FME_NUM_CONDITIONS2___
      REMOVE LongName
      RENAME_SET_VALUE Pset_DoorCommon.Reference > uro_ifc_pset_door_common_uro_reference
      RENAME_SET_VALUE Pset_DoorCommon.AcousticRating > uro_ifc_pset_door_common_uro_acoustic_rating
      RENAME_SET_VALUE Pset_DoorCommon.FireRating > uro_ifc_pset_door_common_uro_firerating
      RENAME_SET_VALUE Pset_DoorCommon.SecurityRating > uro_ifc_pset_door_common_uro_security_rating
      RENAME_SET_VALUE Pset_DoorCommon.IsExternal > uro_ifc_pset_door_common_uro_is_external
      RENAME_SET_VALUE Pset_DoorCommon.Infiltration > uro_ifc_pset_door_common_uro_infiltration
      RENAME_SET_VALUE Pset_DoorCommon.ThermalTransmittance > uro_ifc_pset_door_common_uro_thermal_transmittance
      RENAME_SET_VALUE Pset_DoorCommon.GlazingAreaFraction > uro_ifc_pset_door_common_uro_glazing_area_fraction
      RENAME_SET_VALUE Pset_DoorCommon.HandicapAccessible > uro_ifc_pset_door_common_uro_handicap_accessible
      RENAME_SET_VALUE Pset_DoorCommon.FireExit > uro_ifc_pset_door_common_uro_fire_exit
      RENAME_SET_VALUE Pset_DoorCommon.SelfClosing > uro_ifc_pset_door_common_uro_self_closing
      RENAME_SET_VALUE Pset_CoorCommon.SmokeStop > uro_ifc_pset_door_common_uro_smoke_stop
    -> GeometryRemover_2

Bookmark: Pset_OpeningElementCommon プロパティ抽出
GeometryPartExtractor_2
    GQUERY:
      for $geom in //geometry
      where $geom/@fme_geometry_name = 'Pset_OpeningElementCommon'
      return number($geom/@fme_id)
    EXTRACTED -> GeometryPropertyExtractor_2
    UNTOUCHED -> AttributeManager_OpeningElement
GeometryPropertyExtractor_2
    EXTRACTTYPE_PARAM = Traits
    GQUERY:
      for $geom in //geometry
      where $geom/count(parent::geometry) = 0
      return number($geom/@fme_id)
    PREFIX_EXTRACTED_TRAITS = Yes
    EXTRACTED -> Aggregator_3
Aggregator_3
    ACCUM_ATTRS_NAME = Merge Incoming Attributes
    GROUP_BY = ifc_unique_id
    MODE = Attributes Only
    SEP = ,
    AGGREGATE -> AttributeExposer_3
AttributeExposer_3
    ATTR_LIST = Pset_OpeningElementCommon.Reference,Pset_OpeningElementCommon.Purpose,Pset_OpeningElementCommon.FireExit,Pset_OpeningElementCommon.ProtectedOpening,Pset_OpeningElementCommon.ParallelJambs
    -> AttributeManager_OpeningElement
AttributeManager_OpeningElement
    ATTR_TABLE:
      RENAME_SET_VALUE GlobalId > uro_ifc_opening_element_uro_global_id
      RENAME_SET_VALUE Name > uro_ifc_opening_element_uro_name
      SET_TO uro_ifc_opening_element_uro_description = @Value(gml_description)
      REMOVE LongName
      RENAME_SET_VALUE ObjectType > uro_ifc_opening_element_uro_object_type
      RENAME_SET_VALUE Tag > uro_ifc_opening_element_uro_tag
      REMOVE gml_description
      REMOVE gml_name
      REMOVE OverallHeight
      REMOVE OverallWidth
      RENAME_SET_VALUE Pset_OpeningElementCommon.Reference > uro_ifc_pset_opening_element_common_uro_reference
      RENAME_SET_VALUE Pset_OpeningElementCommon.Purpose > uro_ifc_pset_opening_element_common_uro_purpose
      RENAME_SET_VALUE Pset_OpeningElementCommon.FireExit > uro_ifc_pset_opening_element_common_uro_fire_exit
      RENAME_SET_VALUE Pset_OpeningElementCommon.ProtectedOpening > uro_ifc_pset_opening_element_common_uro_protected_opening
      RENAME_SET_VALUE Pset_OpeningElementCommon.ParallelJambs > uro_ifc_pset_opening_element_common_uro_parallel_jambs
    -> GeometryRemover_3

FME custom transformer PLATEAU.IfcReprojectionParamsExtractor

Parameters:
- FME_PROCESS_GROUP_BY =   # "" Group By
- FME_PROCESS_GROUPS_ORDERED = No   # When All Features Received,No%When Group Changes (Advanced),Yes Complete Groups

IfcFeatures (input)
    -> FeatureTypeFilter
FeatureTypeFilter
    ATTRIBUTES = IfcProject,<Blank>,<Unfiltered>
    IfcProject -> GeometryPartExtractor
    <UNFILTERED> -> Junction
GeometryPartExtractor
    GQUERY:
      for $geom in //geometry
      where $geom/parent::geometry/@fme_geometry_name = 'IfcPropertySet'
      return number($geom/@fme_id)
    EXTRACTED -> GeometryPropertyExtractor
    UNTOUCHED -> <Rejected> (output)
GeometryPropertyExtractor
    EXTRACTTYPE_PARAM = Traits
    GQUERY:
      for $geom in //geometry
      where $geom/count(parent::geometry) = 0
      return number($geom/@fme_id)
    PREFIX_EXTRACTED_TRAITS = Yes
    EXTRACTED -> AttributeExposer
AttributeExposer
    ATTR_LIST = ifc_unique_id,GlobalId,OwnerHistory,Name,Description,ObjectType,LongName,lengthunit,ePSet_ProjectedCRS.Name,ePSet_ProjectedCRS.Description,ePSet_ProjectedCRS.GeodeticDatum,ePSet_ProjectedCRS.VerticalDatum,ePSet_ProjectedCRS.MapProjection,ePSet_ProjectedCRS.MapZone,ePSet_MapConversion.Eastings,ePSet_MapConversion.Northings,ePSet_MapConversion.OrthogonalHeight,ePSet_MapConversion.XAxisAbscissa,ePSet_MapConversion.XAxisOrdinate,ePSet_MapConversion.Scale,fme_basename
    -> Aggregator
Aggregator
    ACCUM_ATTRS_NAME = Merge Incoming Attributes
    GROUP_BY = fme_basename
    MODE = Attributes Only
    SEP = ,
    AGGREGATE -> JSONTemplater [ROOT]
JSONTemplater
    RESULT_ATTRIBUTE = _reprojection_params
    ROOT_QUERY_EXPR:
      {
          "lengthunit" : fme:get-attribute("lengthunit"),
          "ProjectedCRS" : {
              "Name" : fme:get-attribute("ePSet_ProjectedCRS.Name"),
              "Description" : fme:get-attribute("ePSet_ProjectedCRS.Description"),
              "GeodeticDatum" : fme:get-attribute("ePSet_ProjectedCRS.GeodeticDatum"),
              "VerticalDatum" : fme:get-attribute("ePSet_ProjectedCRS.VerticalDatum"),
              "MapProjection" : fme:get-attribute("ePSet_ProjectedCRS.MapProjection"),
              "MapZone" : fme:get-attribute("ePSet_ProjectedCRS.MapZone")
          },
          "MapConversion" : {
              "Eastings" : xs:double(fme:get-attribute("ePSet_MapConversion.Eastings")),
              "Northings" : xs:double(fme:get-attribute("ePSet_MapConversion.Northings")),
              "OrthogonalHeight" : xs:double(fme:get-attribute("ePSet_MapConversion.OrthogonalHeight")),
              "XAxisAbscissa" : xs:double(fme:get-attribute("ePSet_MapConversion.XAxisAbscissa")),
              "XAxisOrdinate" : xs:double(fme:get-attribute("ePSet_MapConversion.XAxisOrdinate")),
              "Scale" : xs:double(fme:get-attribute("ePSet_MapConversion.Scale"))
          }
      }
    VISIBLE_QUERY_VALIDATE = Yes
    -> AttributeManager
AttributeManager
    ATTR_TABLE:
      RENAME_SET_VALUE GlobalId > IfcProject.GlobalId
      RENAME_SET_VALUE OwnerHistory > IfcProject.OwnerHistory
      RENAME_SET_VALUE Name > IfcProject.Name
      RENAME_SET_VALUE Description > IfcProject.Description
      RENAME_SET_VALUE ObjectType > IfcProject.ObjectType
      RENAME_SET_VALUE LongName > IfcProject.LongName
      RENAME_SET_VALUE ePSet_ProjectedCRS.Name > ProjectedCRS.Name
      RENAME_SET_VALUE ePSet_ProjectedCRS.Description > ProjectedCRS.Description
      RENAME_SET_VALUE ePSet_ProjectedCRS.GeodeticDatum > ProjectedCRS.GeodeticDatum
      RENAME_SET_VALUE ePSet_ProjectedCRS.VerticalDatum > ProjectedCRS.VerticalDatum
      RENAME_SET_VALUE ePSet_ProjectedCRS.MapProjection > ProjectedCRS.MapProjection
      RENAME_SET_VALUE ePSet_ProjectedCRS.MapZone > ProjectedCRS.MapZone
      RENAME_SET_VALUE ePSet_MapConversion.Eastings > MapConversion.Eastings
      RENAME_SET_VALUE ePSet_MapConversion.Northings > MapConversion.Northings
      RENAME_SET_VALUE ePSet_MapConversion.OrthogonalHeight > MapConversion.OrthogonalHeight
      RENAME_SET_VALUE ePSet_MapConversion.XAxisAbscissa > MapConversion.XAxisAbscissa
      RENAME_SET_VALUE ePSet_MapConversion.XAxisOrdinate > MapConversion.XAxisOrdinate
      RENAME_SET_VALUE ePSet_MapConversion.Scale > MapConversion.Scale
      RENAME_SET_VALUE lengthunit > _lengthunit
      SET_TO _lengthmultiplier = FME_CONDITIONAL:DEFAULT_VALUE'1'BOOL_OP;OR;COMPOSITE_TEST;1;TEST @Value(_lengthunit) IN millimetre,millimeter'0.001'FME_NUM_CONDITIONS2___
      SET_TO _coordinate_precision = FME_CONDITIONAL:DEFAULT_VALUE'4'BOOL_OP;OR;COMPOSITE_TEST;1;TEST @Value(_lengthunit) IN millimetre,millimeter'1'FME_NUM_CONDITIONS2___
    USER_EXPOSED_ATTRIBUTES = IfcProject.OwnerHistory,OwnerHistory,_georeferencing_parameters
    -> IfcProject (output)
    -> AttributeKeeper
IfcProject (output)
AttributeKeeper
    CREATE_BULK_MODE_FEATURES = NO
    KEEP_ATTRS = _reprojection_params,_lengthunit,_lengthmultiplier,_coordinate_precision
    -> FeatureMerger [SUPPLIER]
<Rejected> (output)
Note: FeatureMerger : Requestor
Junction
    -> Junction_2
Note: FeatureTypeFilter : <Unfiltered>
Junction_2
    -> FeatureMerger [REQUESTOR]
Note: IfcProjectが読み終わるのを待つ
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Others (output)
Others (output)
